-- -----------------------------------------------------------------------------
-- MIB NAME : Secure Shell Common mib
-- FILE NAME: SSH.mib
-- DATE     : 2009/12/21
-- VERSION  : 2.02
-- PURPOSE  : To construct the MIB structure of Secure Shell management
--            for proprietary enterprise
-- -----------------------------------------------------------------------------
-- MODIFICTION HISTORY:
-- -----------------------------------------------------------------------------
-- Version, Date, Author
-- Description:
--  [New Object]
--  [Modification]
-- Notes: (Requested by who and which project)
--
-- Version 2.02, 2009/12/21, Dandelion
-- Description:
--   Add swSSHUserHostIPv6Addr for supporting SSH IPv6 Host_based method authentication.
--
-- Version 2.01, 2008/06/17, Green
-- Description:
--   Correct the object name from swSSHEncryptAlgCAST28Admin to 
--   swSSHEncryptAlgCAST128Admin.
--
-- Version 2.00, 2007/03/27, Yedda
-- This is the first formal version for universal MIB definition.
-- -----------------------------------------------------------------------------

SSH-MIB DEFINITIONS ::= BEGIN


IMPORTS
 	IpAddress
 	    FROM RFC1155-SMI
	Ipv6Address	             	
           FROM IPV6-TC
    MODULE-IDENTITY, OBJECT-TYPE
        FROM SNMPv2-SMI
    RowStatus,DisplayString
            FROM SNMPv2-TC
    MODULE-COMPLIANCE, OBJECT-GROUP
        FROM SNMPv2-CONF
    SnmpAdminString
	FROM SNMP-FRAMEWORK-MIB
	dlink-common-mgmt	FROM DLINK-ID-REC-MIB;


    swSSHMIB MODULE-IDENTITY
        LAST-UPDATED "0912210000Z"
        ORGANIZATION "D-Link Corp."
        CONTACT-INFO
            "http://support.dlink.com"
        DESCRIPTION
            "The Secure Shell module MIB."
        ::= { dlink-common-mgmt 6}

    swSSHMgmt OBJECT IDENTIFIER ::= { swSSHMIB 1 }

-- -----------------------------------------------------------------------------
-- Textual Conventions
-- -----------------------------------------------------------------------------
    swSSHVersion OBJECT-TYPE
        SYNTAX  INTEGER(1..10)
        MAX-ACCESS  read-only
        STATUS  current
        DESCRIPTION
            "This object indicates the SSH version supported in the system."
        ::= { swSSHMgmt 1}

    swSSHAdmin OBJECT-TYPE
        SYNTAX  INTEGER {
                    other(1),
                    disabled(2),
                    enabled(3)
                }
        MAX-ACCESS  read-write
        STATUS  current
        DESCRIPTION
            "This object indicates if the Secure Shell is enabled or disabled."
        ::= { swSSHMgmt 2}

    swSSHMaxAuthFailAttempts OBJECT-TYPE
        SYNTAX  INTEGER (2..20)
        MAX-ACCESS  read-write
        STATUS  current
        DESCRIPTION
            "This object indicates the maximum AAC authentication attempts allowed."
        ::= { swSSHMgmt 3}
    swSSHSessionKeyRekeying OBJECT-TYPE
        SYNTAX  INTEGER {
                        never(0),
                        ten-min(10),
                        thirty-min(30),
                        sixty-min(60)
                       }
        MAX-ACCESS  read-write
        STATUS  current
        DESCRIPTION
            "This object indicates the time interval in minutes to negotiate new session keys
            for client and server."
        ::= { swSSHMgmt 4}

    swSSHMaxSession OBJECT-TYPE
        SYNTAX  INTEGER(1..8)
        MAX-ACCESS  read-write
        STATUS  current
        DESCRIPTION
            "This object indicates the SSH supported max session for the system."
        ::= { swSSHMgmt 5}

    swSSHConnectionTimeout OBJECT-TYPE
        SYNTAX  INTEGER(120..600)
        MAX-ACCESS  read-write
        STATUS  current
        DESCRIPTION
            "This object indicates connection timeout."
        ::= { swSSHMgmt 6}

    swSSHListenedPort OBJECT-TYPE
        SYNTAX  INTEGER(1..65535)
        MAX-ACCESS  read-write
        STATUS  current
        DESCRIPTION
            "This object indicates listened port."
        ::= { swSSHMgmt 7}


-- -----------------------------------------------------------------------------
-- groups in the SSH MIB
-- -----------------------------------------------------------------------------


-- -----------------------------------------------------------------------------
    swSSHCtrlAlgGroup OBJECT IDENTIFIER ::= { swSSHMIB 3 }

    swSSHEncryptAlgCtrl OBJECT IDENTIFIER ::= { swSSHCtrlAlgGroup 1 }

    swSSHEncryptAlg3DESAdmin OBJECT-TYPE
        SYNTAX  INTEGER {
                    other(1),
                    disabled(2),
                    enabled(3)
                }
        MAX-ACCESS  read-write
        STATUS  current
        DESCRIPTION
            "This object indicates if the DES encryption algorithm is enabled or disabled."
        ::= { swSSHEncryptAlgCtrl 1}

    swSSHEncryptAlgBlowfishAdmin OBJECT-TYPE
        SYNTAX  INTEGER {
                    other(1),
                    disabled(2),
                    enabled(3)
                }
        MAX-ACCESS  read-write
        STATUS  current
        DESCRIPTION
            "This object indicates if the Blowfish encryption algorithm is enabled or disabled
    		."
        ::= { swSSHEncryptAlgCtrl 2}

    swSSHEncryptAlgAES128Admin OBJECT-TYPE
        SYNTAX  INTEGER {
                    other(1),
                    disabled(2),
                    enabled(3)
                }
        MAX-ACCESS  read-write
        STATUS  current
        DESCRIPTION
            "This object indicates if the AES128 encryption algorithm is enabled or disabled
    		."
        ::= { swSSHEncryptAlgCtrl 3}

    swSSHEncryptAlgAES192Admin OBJECT-TYPE
        SYNTAX  INTEGER {
                    other(1),
                    disabled(2),
                    enabled(3)
                }
        MAX-ACCESS  read-write
        STATUS  current
        DESCRIPTION
            "This object indicates if the AES192 encryption algorithm is enabled or disabled."
        ::= { swSSHEncryptAlgCtrl 4}

    swSSHEncryptAlgAES256Admin OBJECT-TYPE
        SYNTAX  INTEGER {
                    other(1),
                    disabled(2),
                    enabled(3)
                }
        MAX-ACCESS  read-write
        STATUS  current
        DESCRIPTION
            "This object indicates if the AES256 encryption algorithm is enabled or disabled."
        ::= { swSSHEncryptAlgCtrl 5}

    swSSHEncryptAlgArcfourAdmin OBJECT-TYPE
        SYNTAX  INTEGER {
                    other(1),
                    disabled(2),
                    enabled(3)
                }
        MAX-ACCESS  read-write
        STATUS  current
        DESCRIPTION
            "This object indicates if the Arcfour encryption algorithm is enabled or disabled."
        ::= { swSSHEncryptAlgCtrl 6}

    swSSHEncryptAlgCAST128Admin OBJECT-TYPE
        SYNTAX  INTEGER {
                    other(1),
                    disabled(2),
                    enabled(3)
                }
        MAX-ACCESS  read-write
        STATUS  current
        DESCRIPTION
            "This object indicates if the CAST128 encryption algorithm is enabled or disabled."
        ::= { swSSHEncryptAlgCtrl 7}

    swSSHEncryptAlgTwofish128Admin OBJECT-TYPE
        SYNTAX  INTEGER {
                    other(1),
                    disabled(2),
                    enabled(3)
                }
        MAX-ACCESS  read-write
        STATUS  current
        DESCRIPTION
            "This object indicates if the Twofish128 encryption algorithm is enabled or disabled."
        ::= { swSSHEncryptAlgCtrl 8}

    swSSHEncryptAlgTwofish192Admin OBJECT-TYPE
        SYNTAX  INTEGER {
                    other(1),
                    disabled(2),
                    enabled(3)
                }
        MAX-ACCESS  read-write
        STATUS  current
        DESCRIPTION
            "This object indicates if the Twofish192 encryption algorithm is enabled or disabled."
        ::= { swSSHEncryptAlgCtrl 9}

    swSSHEncryptAlgTwofish256Admin OBJECT-TYPE
        SYNTAX  INTEGER {
                    other(1),
                    disabled(2),
                    enabled(3)
                }
        MAX-ACCESS  read-write
        STATUS  current
        DESCRIPTION
            "This object indicates if the Twofish256 encryption algorithm is enabled or disabled."
        ::= { swSSHEncryptAlgCtrl 10}


-- -----------------------------------------------------------------------------
    swSSHAuthenMethodCtrl OBJECT IDENTIFIER ::= { swSSHCtrlAlgGroup 2 }

    swSSHAuthenMethodPasswdAdmin OBJECT-TYPE
        SYNTAX  INTEGER {
                    other(1),
                    disabled(2),
                    enabled(3)
                }
        MAX-ACCESS  read-write
        STATUS  current
        DESCRIPTION
            "This object indicates if the password authentication is enabled or disabled."
        ::= { swSSHAuthenMethodCtrl 1}

    swSSHAuthenMethodPubKeyAdmin OBJECT-TYPE
        SYNTAX  INTEGER {
                    other(1),
                    disabled(2),
                    enabled(3)
                }
        MAX-ACCESS  read-write
        STATUS  current
        DESCRIPTION
            "This object indicates if the Public Key authentication is enabled or disabled."
        ::= { swSSHAuthenMethodCtrl 2}

    swSSHAuthenMethodHostKeyAdmin OBJECT-TYPE
        SYNTAX  INTEGER {
                    other(1),
                    disabled(2),
                    enabled(3)
                }
        MAX-ACCESS  read-write
        STATUS  current
        DESCRIPTION
            "This object indicates if the Host Key authentication is enabled or disabled."
        ::= { swSSHAuthenMethodCtrl 3}

-- -----------------------------------------------------------------------------
    swSSHInteAlgCtrl OBJECT IDENTIFIER ::= { swSSHCtrlAlgGroup 3 }

    swSSHInteAlgSHA1Admin OBJECT-TYPE
        SYNTAX  INTEGER {
                    other(1),
                    disabled(2),
                    enabled(3)
                }
        MAX-ACCESS  read-write
        STATUS  current
        DESCRIPTION
            "This object indicates if the HMAC-SHA1 algorithm is enabled or disabled."
        ::= { swSSHInteAlgCtrl 1}

    swSSHInteAlgMD5Admin OBJECT-TYPE
        SYNTAX  INTEGER {
                    other(1),
                    disabled(2),
                    enabled(3)
                }
        MAX-ACCESS  read-write
        STATUS  current
        DESCRIPTION
            "This object indicates if the HMAC-MD5 algorithm is enabled or disabled."
        ::= { swSSHInteAlgCtrl 2}


--  swSSHKeyExDAdmin OBJECT IDENTIFIER ::= { swSSHCtrlAlgGroup 4 }

--   swSSHKeyExDAdmin OBJECT-TYPE
--        SYNTAX  INTEGER {
--                    other(1),
--                    disabled(2),
--                    enabled(3)
--                }
--        MAX-ACCESS  read-write
--        STATUS  current
--        DESCRIPTION
--            "This object indicates if the Diffie Hellman algorithm is enabled or disabled
--			."
--        ::= { swSSHCtrlAlgGroup 4}

-- -----------------------------------------------------------------------------
    swSSHPublKeyCtrl OBJECT IDENTIFIER ::= { swSSHCtrlAlgGroup 5 }

    swSSHPublKeyRSAAdmin OBJECT-TYPE
        SYNTAX  INTEGER {
                    other(1),
                    disabled(2),
                    enabled(3)
                }
        MAX-ACCESS  read-write
        STATUS  current
        DESCRIPTION
            "This object indicates if the RSA algorithm is enabled or disabled."
        ::= { swSSHPublKeyCtrl 1}

    swSSHPublKeyDSAAdmin OBJECT-TYPE
        SYNTAX  INTEGER {
                    other(1),
                    disabled(2),
                    enabled(3)
                }
        MAX-ACCESS  read-write
        STATUS  current
        DESCRIPTION
            "This object indicates if the DSA algorithm is enabled or disabled."
        ::= { swSSHPublKeyCtrl 2}

-- -----------------------------------------------------------------------------
-- SSH User Info Management
-- -----------------------------------------------------------------------------
    swSSHUserMgmt 	OBJECT IDENTIFIER ::= {swSSHMIB 4}

    swSSHUserCtrlTable OBJECT-TYPE
    	SYNTAX SEQUENCE OF SshUserEntry
    		MAX-ACCESS not-accessible
            STATUS current
            DESCRIPTION
            	"The SSH user table."
            ::= { swSSHUserMgmt 1 }

    swSSHUserCtrlEntry OBJECT-TYPE
    		SYNTAX SshUserEntry
            MAX-ACCESS not-accessible
            STATUS current
            DESCRIPTION
            	"The entries of SSH user table."
            INDEX  { swSSHUserName }
            ::= { swSSHUserCtrlTable 1 }

    SshUserEntry ::=
    	SEQUENCE {
    		swSSHUserName 		SnmpAdminString,
    		swSSHUserAuthMode	INTEGER,
    		swSSHUserHostName	SnmpAdminString,
    		swSSHUserHostIPAddr 	IpAddress,
    		swSSHUserHostIPv6Addr 	Ipv6Address
    	}

    swSSHUserName OBJECT-TYPE
    	SYNTAX	SnmpAdminString (SIZE(1..15))
    	MAX-ACCESS read-only
    	STATUS	current
    	DESCRIPTION
    		"SSH user name."
    	::= { swSSHUserCtrlEntry 1 }

    swSSHUserAuthMode OBJECT-TYPE
    	SYNTAX INTEGER {
    		hostbased(1),
    		password(2),
    		publickey(3)
    		}
    	MAX-ACCESS read-write
    	STATUS current
    	DESCRIPTION
    		"Specifies the auth mode for a user."
    	::= { swSSHUserCtrlEntry 2 }

    swSSHUserHostName OBJECT-TYPE
    	SYNTAX SnmpAdminString (SIZE(1..32))
    	MAX-ACCESS read-write
    	STATUS current
    	DESCRIPTION
    		"Specifies the host name of host-based auth mode."
    	::= { swSSHUserCtrlEntry 3 }

    swSSHUserHostIPAddr OBJECT-TYPE
    	SYNTAX IpAddress
    	MAX-ACCESS read-write
    	STATUS current
    	DESCRIPTION
    		"Specifies the host IP address of host-based auth mode."
    	::= { swSSHUserCtrlEntry 4 }

   swSSHUserHostIPv6Addr OBJECT-TYPE
        SYNTAX  	Ipv6Address
        MAX-ACCESS  read-write
        STATUS  	current
        DESCRIPTION
    		"Specifies the host IPv6 address of host-based auth mode."
    	::= { swSSHUserCtrlEntry 5 }
END
