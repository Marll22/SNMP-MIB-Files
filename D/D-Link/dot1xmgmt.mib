-- -----------------------------------------------------------------------------
-- MIB NAME : 802.1x guest VLAN Common mib
-- FILE NAME: dot1xmgmt.mib
-- DATE     : 2007/03/27
-- VERSION  : 2.00
-- PURPOSE  : To construct the MIB structure of 802.1x guest VLAN management
--            for proprietary enterprise
-- -----------------------------------------------------------------------------
-- MODIFICTION HISTORY:
-- -----------------------------------------------------------------------------
-- Version, Date, Author
-- Description:
--  [New Object]
--  [Modification]
-- Notes: (Requested by who and which project)
--
-- Version 2.00, 2007/03/27, Yedda
-- This is the first formal version for universal MIB definition.
-- -----------------------------------------------------------------------------

Dot1xMGMT-MIB DEFINITIONS ::= BEGIN
    IMPORTS
        TEXTUAL-CONVENTION	, DisplayString
        								FROM SNMPv2-TC
        MODULE-IDENTITY, OBJECT-TYPE,
        Integer32						FROM SNMPv2-SMI
        dlink-common-mgmt				FROM DLINK-ID-REC-MIB;

	swdot1xMGMTMIB  MODULE-IDENTITY
	    LAST-UPDATED "0703270000Z"
	    ORGANIZATION "D-Link Corp."
	    CONTACT-INFO
	        "http://support.dlink.com"
	    DESCRIPTION
		    "The Structure of 802.1X guest VLAN for the proprietary enterprise."
		    ::= { dlink-common-mgmt 30 }


PortList                ::= OCTET STRING(SIZE (0..127))

dot1xGuestVlan        OBJECT IDENTIFIER ::= { swdot1xMGMTMIB 1 }


-- -----------------------------------------------------------------------------
-- The Guest Vlan Group
-- -----------------------------------------------------------------------------
dot1xGuestVlanName OBJECT-TYPE
    SYNTAX      DisplayString(SIZE(1..32))
    MAX-ACCESS  read-write
    STATUS      current
    DESCRIPTION
        "The VLAN name of guest VLAN."
    ::= { dot1xGuestVlan 1 }

dot1xGuestVlanPort OBJECT-TYPE
    SYNTAX      PortList
    MAX-ACCESS  read-write
    STATUS      current
    DESCRIPTION
        "This object indicates the guest VLAN port members of this device."
     ::= { dot1xGuestVlan 2 }

dot1xGuestVlanDelState OBJECT-TYPE
    SYNTAX      INTEGER{
    		none(1),
    		start(2)
    		}
    MAX-ACCESS  read-write
    STATUS      current
    DESCRIPTION
        "Used to delete the guest VLAN."
    ::= { dot1xGuestVlan 3 }

END
