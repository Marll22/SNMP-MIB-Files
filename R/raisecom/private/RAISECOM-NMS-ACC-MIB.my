--MibName=raisecomNMSAccessControl
-- =======================================================================
-- Version info 
--
-- Version 0.1 Created 2003.5.24 by GONGGUIDONG
-- This version of MIB is created just for management of base and user. 
-- 
-- Copyright(c) 2000-2002 by Raisecom  Ltd. 

-- delete  raisecomSnmpAccessControlStatus 	by gongguidong 20030819
-- add iscom4124  iscom2126  metrocom3000     	by gongguidong 20040205
-- =======================================================================


RAISECOM-NMS-ACC-MIB DEFINITIONS ::= BEGIN

	IMPORTS
		MODULE-IDENTITY,
		OBJECT-TYPE,
		Counter32,
		Integer32,
		IpAddress,
		enterprises,
		Unsigned32
			FROM SNMPv2-SMI
		DisplayString,
		RowStatus,
		TruthValue
			FROM SNMPv2-TC
		raisecomAgent		
			FROM RAISECOM-BASE-MIB;
		
        raisecomNMSAccessControl MODULE-IDENTITY
                LAST-UPDATED "200402060000Z"
                ORGANIZATION "raisecom, Ltd."
                CONTACT-INFO "www.raisecom.com"
                DESCRIPTION  "raisecom NMS-Access-Control objects"
        ::= { raisecomAgent 5 }



	
	
	-- The raisecomNMSAccessProfile Group
	--
	--	The raisecomNMSAccessProfileGroup objects for
	--	identifying  NMS which can access and manage switch.  It consists of the
	--	raisecomNMSACPTable and the raisecomNMSACPAddressTable.
	

	--
	-- The raisecom NMS Access Profile Address Table.
	--
	--

	raisecomNMSACPAddressTable OBJECT-TYPE
		SYNTAX  SEQUENCE OF RaisecomNMSACPAddressentry 
		MAX-ACCESS  not-accessible
		STATUS current
		DESCRIPTION
			"This table lists all addresses in access profile."
		::= { raisecomNMSAccessControl 1 }



	raisecomNMSACPAddressEntry OBJECT-TYPE
		SYNTAX   RaisecomNMSACPAddressentry 
		MAX-ACCESS  not-accessible
		STATUS current
		DESCRIPTION
			"A  raisecomNMSACPAddressentry contains address info 
			of NMS Access profile."
		INDEX	{  raisecomNMSACPAddrIndex }
		::= {  raisecomNMSACPAddressTable 1 }
	
	RaisecomNMSACPAddressentry ::=
		SEQUENCE {
			 raisecomNMSACPAddrIndex
				INTEGER (0..99),
			 raisecomNMSACPAddrIPAddress
				IpAddress,
			 raisecomNMSACPAddrNetMask
				IpAddress,
			 raisecomNMSACPAddrRowStatus
				RowStatus	
		}
	
	raisecomNMSACPAddrIndex OBJECT-TYPE
		SYNTAX  INTEGER (0..99)
		MAX-ACCESS	read-only
		STATUS          current
		DESCRIPTION
		  "The index of the raisecom NMS Access Profile Address Entry."
		::= { raisecomNMSACPAddressEntry 1 }
	
	
	raisecomNMSACPAddrIPAddress OBJECT-TYPE
		SYNTAX  IpAddress 
		MAX-ACCESS  read-create
		STATUS current
		DESCRIPTION
		    "The IP network number for the raisecom NMS 
		     Access Profile Address Entry."
		::= {  raisecomNMSACPAddressEntry 2 }
	
	raisecomNMSACPAddrNetMask OBJECT-TYPE
		SYNTAX  IpAddress 
		MAX-ACCESS  read-create
		STATUS current
		DESCRIPTION
			"The IP network mask corresponding to the IP Network
			address defined by  raisecomNMSACPAddrIPAddress."
		::= {  raisecomNMSACPAddressEntry 3 }
	
	raisecomNMSACPAddrRowStatus OBJECT-TYPE
		SYNTAX  RowStatus
		MAX-ACCESS  read-create
		STATUS current
		DESCRIPTION
		"to indicate if this row is active or inactive ."
			::= {  raisecomNMSACPAddressEntry 4 }



	--
	-- The raisecom Telnet NMS Access Config Table.
	--
	--
	
	raisecomTelnetAccessControlStatus OBJECT-TYPE
		SYNTAX  	INTEGER{
			    	enable(1),
			    	disable(0)
				}    
		MAX-ACCESS  read-write
		STATUS current
		DESCRIPTION
			"This object is to open or close the function of telnet
			 accesscontrol."
		::= { raisecomNMSAccessControl 2 }
		
	raisecomWebAccessControlStatus OBJECT-TYPE
		SYNTAX  	INTEGER{
			    	enable(1),
			    	disable(0)
				}    
		MAX-ACCESS  read-write
		STATUS current
		DESCRIPTION
			"This object is to open or close the function of web
			 accesscontrol."
		::= { raisecomNMSAccessControl 3 }					
		

END
