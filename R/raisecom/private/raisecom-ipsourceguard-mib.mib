--MibName=rcIpSourceGuard
-- *****************************************************************
-- RAISECOM-RC3026BANDWIDTHMANAGE-MIB.MIB:  Raisecom Bandwidth Manage MIB file
--
-- June 2008, dongxiaogang
--
-- Copyright (c) 1994-2008 by Raisecom, Inc.
-- All rights reserved.
-- 
-- *****************************************************************
RAISECOM-IPSOURCEGUARD-MIB  DEFINITIONS ::= BEGIN

IMPORTS
        iscomSwitch			
         		FROM RAISECOM-BASE-MIB
        RowStatus,MacAddress
                FROM SNMPv2-TC
        EnableVar
                FROM SWITCH-TC
        rcPortIndex
                FROM SWITCH-SYSTEM-MIB;                
                 
     rcIpSourceGuard MODULE-IDENTITY
        LAST-UPDATED    "200412200000Z"
        ORGANIZATION    "Raisecom, Inc."
        CONTACT-INFO
                "       Raise Systems
                        
                Postal: Beijing,
                        China

                   Tel: 86-010-82884499

                E-mail: dongxiaogang@raisecom.com"
        DESCRIPTION
                "description of Ip Source Guard object."
                
        REVISION    "200909090000Z"  -- Sep  09, 2009
        DESCRIPTION "Version 1.1,change rcIpVerifySourceCurrentEntryNum,rcIpVerifySourceMaxEntryNum to read-only"

        ::= { iscomSwitch 37}    
  
        rcIpVerifySource OBJECT-TYPE 
        SYNTAX EnableVar 
        MAX-ACCESS read-write
        STATUS current
        DESCRIPTION
            "The statis bind enable or disable." 
        DEFVAL { disable }
        ::= { rcIpSourceGuard 1}
 
       rcIpVerifySourceDhcpsnooping OBJECT-TYPE 
        SYNTAX EnableVar 
        MAX-ACCESS read-write
        STATUS current
        DESCRIPTION
            "The dynamic bind enable or disable."  
        DEFVAL { disable }
         ::= { rcIpSourceGuard 2}
 
        rcIpVerifySourceMaxEntryNum OBJECT-TYPE 
        SYNTAX INTEGER 
        MAX-ACCESS read-only
        STATUS current
        DESCRIPTION
            "The MAX bind entry number."  
        DEFVAL { 0 }    
        ::= { rcIpSourceGuard 3}

        rcIpVerifySourceCurrentEntryNum OBJECT-TYPE 
        SYNTAX INTEGER 
        MAX-ACCESS read-only
        STATUS current
        DESCRIPTION
            "The current entry number."    
        DEFVAL { 0 }    
        ::= { rcIpSourceGuard 4}

       rcPortTrustTable OBJECT-TYPE
        SYNTAX SEQUENCE OF RcPortTrustEntry
        MAX-ACCESS not-accessible
        STATUS current
        DESCRIPTION
            "enable statis or dynamic bind type."
        ::= { rcIpSourceGuard 5}  
                
       rcPortTrustEntry OBJECT-TYPE
        SYNTAX RcPortTrustEntry
        MAX-ACCESS not-accessible
        STATUS current
        DESCRIPTION
            "Table entry for ip Source Guard ."
        INDEX { rcPortIndex }
		     ::= { rcPortTrustTable 1 }


       RcPortTrustEntry ::= SEQUENCE {
          rcPortIpVerifySourceTrust  EnableVar
       }
      
       rcPortIpVerifySourceTrust   OBJECT-TYPE
          SYNTAX    EnableVar 
          ACCESS    read-write
          STATUS    current  
          DESCRIPTION
                 "enable or disable the dynamic port bind."
          DEFVAL { disable }
          ::= { rcPortTrustEntry 1} 
      
  ---------------------------------ip Source Gurad table-------------  
     rcIpSourceGuardTable OBJECT-TYPE
        SYNTAX SEQUENCE OF RcIpSourceGuardEntry
        MAX-ACCESS not-accessible
        STATUS current
        DESCRIPTION
            "A table of ip Source Guard."
        ::= { rcIpSourceGuard 6}

    rcIpSourceGuardEntry OBJECT-TYPE
        SYNTAX RcIpSourceGuardEntry
        MAX-ACCESS not-accessible
        STATUS current
        DESCRIPTION
            "Table entry for ip Source Guard."
        INDEX { rcPortBindIp }
        ::= { rcIpSourceGuardTable 1 }

    RcIpSourceGuardEntry ::= SEQUENCE {
        rcPortBindIp            IpAddress,
        rcPortBindPortid        INTEGER,
        rcPortBindType          INTEGER,
        rcPortBindMac           MacAddress,
        rcPortBindVlan          INTEGER, 
        rcPortBindHwStatus      EnableVar,
        rcPortBindRowStatus     RowStatus
    }  
      
      rcPortBindIp   OBJECT-TYPE
          SYNTAX    IpAddress    
          ACCESS    not-accessible
          STATUS    current
          DESCRIPTION
                 "The bind ip."    
       ::= { rcIpSourceGuardEntry 1 } 
  
      rcPortBindPortid   OBJECT-TYPE
          SYNTAX    INTEGER 
          ACCESS    read-create
          STATUS    current
          DESCRIPTION
                 "the port of the ip source guard applied."  
       ::= { rcIpSourceGuardEntry 2 }    
    
     rcPortBindType   OBJECT-TYPE
          SYNTAX    INTEGER{
               statis(1),
               dynamic-snooping(2),   
               dynamic-relay(3)
          }   
          ACCESS    read-only
          STATUS    current
          DESCRIPTION
                 "statis or dynamic."    
       ::= { rcIpSourceGuardEntry 3 }    
        
     rcPortBindMac   OBJECT-TYPE
          SYNTAX    MacAddress    
          ACCESS    read-create
          STATUS    current
          DESCRIPTION
                 "The bind mac."    
       ::= { rcIpSourceGuardEntry 4 }    
    
    rcPortBindVlan   OBJECT-TYPE
          SYNTAX    INTEGER (0..4094)
          ACCESS    read-create
          STATUS    current
          DESCRIPTION
                 "The bind vlan."    
       ::= { rcIpSourceGuardEntry 5 } 

     rcPortBindHwStatus   OBJECT-TYPE
          SYNTAX    EnableVar 
          ACCESS    read-only
          STATUS    current
          DESCRIPTION
                 "The row status."    
       ::= { rcIpSourceGuardEntry 6 }  
                
     rcPortBindRowStatus   OBJECT-TYPE
          SYNTAX    RowStatus 
          ACCESS    read-create
          STATUS    current
          DESCRIPTION
                 "The row status."    
       ::= { rcIpSourceGuardEntry 7 } 
    
     rcIpVerifySourceAutoUpdate OBJECT-TYPE 
     SYNTAX     EnableVar 
     MAX-ACCESS read-write
     STATUS     current
     DESCRIPTION
         "automaticly import to static table."    
     DEFVAL { disable }    
     ::= { rcIpSourceGuard 7}     
     
       rcIpVerifySourceDhcpRelay OBJECT-TYPE 
        SYNTAX EnableVar 
        MAX-ACCESS read-write
        STATUS current
        DESCRIPTION
            "The dynamic bind enable or disable."  
        DEFVAL { disable }
         ::= { rcIpSourceGuard 8}
     
              
 END
