--MibName=raisecomSystem
-- =======================================================================
-- Version info 
--
-- Version 0.1 Created 2003.12.17 by GONGGUIDONG
-- This version of MIB is created just for the use of Network Management Systems
-- display the  memory and cpu.
--
-- Copyright(c) 2002-2005 by RAISECOM TECH, Ltd.     
-- modify history 
-- 02, 20100220, wangzhongfei, modify ProcessStatus value .
-- 01, 20090915, qiyun, Add CPU monitor MIBs.
--                   
-- =======================================================================



RAISECOM-SYSTEM-MIB DEFINITIONS ::= BEGIN

	IMPORTS
        MODULE-IDENTITY,Unsigned32 
                	FROM SNMPv2-SMI
		OBJECT-TYPE     
					FROM SNMPv2-SMI
		raisecomAgent    
					FROM RAISECOM-BASE-MIB
        EnableVar	
                    FROM SWITCH-TC
        TimeStamp,TEXTUAL-CONVENTION
                    FROM SNMPv2-TC;

	raisecomSystem MODULE-IDENTITY
                LAST-UPDATED 	"200507270000Z"
                ORGANIZATION 	"RAISECOM TECH, Ltd."
                CONTACT-INFO 	"www.raisecom.com"
                DESCRIPTION  	
                		"raisecom System objects: objects common to all platforms."
        	::= { raisecomAgent 1 }	    
--       	
-- Textual Conventions
--
						
    ProcessStatus ::= TEXTUAL-CONVENTION
		STATUS	current
		DESCRIPTION
	   	    	"Status of the process."		
        SYNTAX   INTEGER{
	                      ready(0),
	                      delay(4), 
	                      delay_s(5),
	                      pend(2),
	                      pend_t(6),
	                      pend_s(3),
	                      pend_t_s(7), 
	                      suspend(1),
	                      dead(8)
                        }   
                      
    CPUTimeStamp ::= TEXTUAL-CONVENTION
        DISPLAY-HINT "4d.4d"
        STATUS       current
        DESCRIPTION                
                "The time in seconds that could represent signed
                quantities like time delay with respect to some
                source. The signed integer part is in the first 
                32 bits and the fraction part is in the last 32 bits."
        REFERENCE
                "D.L. Mills, 'Network Time Protocol (Version 3)',
                RFC-1305, March 1992, Sections 2,  3.2.1"
        SYNTAX     OCTET STRING (SIZE (8))


--
-- RAISECOM CPU objects
--   

	raisecomCpu MODULE-IDENTITY
                LAST-UPDATED 	"200412170000Z"
                ORGANIZATION 	"RAISECOM TECH, Ltd."
                CONTACT-INFO 	"www.raisecom.com"
                DESCRIPTION  	
                		"raisecom System objects: objects common to all platforms."
        	::= { raisecomSystem 1 } 
        	
--------------------------------------------------------------------------
--raisecom CPU scalars
--------------------------------------------------------------------------
        
       raisecomCpuBusy1Per OBJECT-TYPE
                   SYNTAX  INTEGER (0..100)
                   UNITS	"percent"
                   ACCESS  read-only
                   STATUS  mandatory
                   DESCRIPTION
                           "CPU busy percentage in the last 1 second
                           period,gathering data at the rate 200 times 
                           per second. Not the last 1 realtime seconds 
                           but the last 1 second period in the scheduler."
                   ::= { raisecomCpu 1 } 
                   
       raisecomCpuBusy60Per OBJECT-TYPE
                   SYNTAX  INTEGER  (0..100)
                   UNITS	"percent"
                   ACCESS  read-only
                   STATUS  mandatory
                   DESCRIPTION
                          "CPU busy percentage in the last 60 second
                           period,gathering data at the rate 200 times 
                           per second. Not the last 60 realtime seconds 
                           but the last 60 second period in the scheduler."
                   ::= { raisecomCpu 2}   
                   
--------------------------------------------------------------------------
--raisecomCPUTrapGroup
-------------------------------------------------------------------------- 
     raisecomCPUTrapGroup  OBJECT IDENTIFIER
                   ::= { raisecomCpu 3 }   
                   
     raisecomCPURisingThreshold NOTIFICATION-TYPE
	        OBJECTS { raisecomProcessIndex, raisecomProcessUtilization, raisecomCPUUtilization }
	        STATUS  current
	        DESCRIPTION
	             "CPU utilization rising threshold trap transfer."
	        ::= { raisecomCPUTrapGroup 1 }
      
     raisecomCPUFallingThreshold NOTIFICATION-TYPE
	        OBJECTS { raisecomCPUUtilization }
	        STATUS  current
	        DESCRIPTION
	             "CPU utilization falling threshold trap transfer."
	        ::= { raisecomCPUTrapGroup 2 }	
	        		                   
--------------------------------------------------------------------------
--raisecomCPUScalarGroup
--------------------------------------------------------------------------   

       raisecomCPUScalarGroup  OBJECT IDENTIFIER
                   ::= { raisecomCpu 4 }

       raisecomCPUUtilizationTotal OBJECT-TYPE
                   SYNTAX  INTEGER  (0..100)
                   UNITS	"percent"
                   ACCESS  read-only
                   STATUS  current
                   DESCRIPTION
                          "CPU busy percentage since system startup."
                   ::= { raisecomCPUScalarGroup 1}  
                   
       raisecomCPUHistoryTableSize OBJECT-TYPE
                   SYNTAX  INTEGER                   
                   ACCESS  read-only
                   STATUS  current                  
                   DESCRIPTION
                          "A value configured by the user which specifies 
                          the number of reports in the history table."  
                   DEFVAL { 60 }
                   ::= { raisecomCPUScalarGroup 2} 
                   
       raisecomCPUThresholdTrapEnable OBJECT-TYPE
                   SYNTAX  EnableVar
                   ACCESS  read-write
                   STATUS  current  
                   DESCRIPTION
                          "The administration status of the CPU utilization threshold trap."
                   ::= { raisecomCPUScalarGroup 3}   
                   
       raisecomCPURisingThresholdValue OBJECT-TYPE
                   SYNTAX  INTEGER  (1..100)
                   ACCESS  read-write
                   STATUS  current                    
                   DESCRIPTION
                          "The percentage rising threshold value configured by the user. 
                          The value indicates, if the CPU utilization which rise from 
                          raisecomCPUFallingThresholdValue is equal to or above this value 
                          for raisecomCPUThresholdInterval duration then send 
                          a raisecomCPURisingThreshold notification to the NMS." 
                   DEFVAL { 100 }
                   ::= { raisecomCPUScalarGroup 4} 
                   
       raisecomCPUFallingThresholdValue OBJECT-TYPE
                   SYNTAX  INTEGER  (1..100)
                   ACCESS  read-write
                   STATUS  current                     
                   DESCRIPTION
                          "The percentage falling threshold value configured by the user. 
                          The value indicates, if the CPU utilization which fell from 
                          raisecomCPURisingThresholdValue is equal to or below this value 
                          for raisecomCPUThresholdInterval duration then send 
                          a raisecomCPUFallingThreshold notification to the NMS."
                   DEFVAL { 1 }
                   ::= { raisecomCPUScalarGroup 5}    
                   
       raisecomCPUThresholdInterval OBJECT-TYPE
                   SYNTAX  INTEGER  (5..36000)
                   ACCESS  read-write
                   STATUS  current                     
                   DESCRIPTION
                          "This is an observation interval.
                          The value of this object indicates that the CPU utilization 
                          should be above raisecomCPURisingThresholdValue for this 
                          duration to send a raisecomCPURisingThreshold notification 
                          to the NMS or below raisecomCPUFallingThresholdValue for 
                          this duration to send a raisecomCPUFallingThreshold."
                   DEFVAL { 60 }
                   ::= { raisecomCPUScalarGroup 6}    
                   
       raisecomCpuTotalProcNum OBJECT-TYPE
                   SYNTAX  INTEGER  (1..256)
                   ACCESS  read-only
                   STATUS  current                     
                   DESCRIPTION
                          "Total number of processes."
                   ::= { raisecomCPUScalarGroup 7}  
                   
       raisecomCPUTrapUtilization OBJECT-TYPE
                   SYNTAX  INTEGER  (0..100)
                   UNITS	"percent"
                   ACCESS  read-only
                   STATUS  current
                   DESCRIPTION
                          "Total CPU utilization within the interval."
                   ::= { raisecomCPUScalarGroup 8}            
  
                   
--------------------------------------------------------------------------
--raisecomCPUTableGroup
--------------------------------------------------------------------------   

       raisecomCPUTableGroup  OBJECT IDENTIFIER
                   ::= { raisecomCpu 5 }

--------------------------------------------------------------------------
--raisecomCPUUtilizationGroup
--------------------------------------------------------------------------   

       raisecomCPUUtilizationGroup  OBJECT IDENTIFIER
                   ::= { raisecomCPUTableGroup 1 }

---------------------------------
--raisecomCPUUtilizationTable
---------------------------------
       raisecomCPUUtilizationTable OBJECT-TYPE
				   SYNTAX  SEQUENCE OF RaisecomCPUUtilizationEntry
				   ACCESS  not-accessible
				   STATUS  current
				   DESCRIPTION
				            "This table contains information about CPU utilization."
				   ::= { raisecomCPUUtilizationGroup 1 }                          
		
	   raisecomCPUUtilizationEntry OBJECT-TYPE
				    SYNTAX  RaisecomCPUUtilizationEntry
				    ACCESS  not-accessible
				    STATUS  current
				    DESCRIPTION
				            "Information about the CPU utilization."
				    INDEX           { raisecomCPUUtilizationIndex } 
				    ::= { raisecomCPUUtilizationTable 1 }
		
	   RaisecomCPUUtilizationEntry ::= SEQUENCE {
			        raisecomCPUUtilizationIndex     INTEGER,
			        raisecomCPUUtilizationPeriod    INTEGER,
			        raisecomCPUUtilization          INTEGER			
			        }  
			        
       raisecomCPUUtilizationIndex OBJECT-TYPE
					SYNTAX  INTEGER 				    
					ACCESS  not-accessible
					STATUS  current
					DESCRIPTION
					"This object index of CPU utilization entry."
					::= { raisecomCPUUtilizationEntry 1 }   
					
	   raisecomCPUUtilizationPeriod OBJECT-TYPE
					SYNTAX	INTEGER {
										oneSec(1), 
										fiveSec(2), 
										oneMin(3),
										tenMin(4),
										twoHour(5)
									}				    
					ACCESS  read-only
					STATUS  current
					DESCRIPTION
					"Periods for computing CPU utilization."
					::= { raisecomCPUUtilizationEntry 2 }     
					
       raisecomCPUUtilization OBJECT-TYPE
					SYNTAX  INTEGER (0..100)
					UNITS	"percent" 				    
					ACCESS  read-only
					STATUS  current
					DESCRIPTION
					"CPU busy percentage in the last specified period."
					::= { raisecomCPUUtilizationEntry 3 }

---------------------------------
--raisecomCPUHistoryTable  
--------------------------------- 
       raisecomCPUHistoryTable OBJECT-TYPE
				   SYNTAX   SEQUENCE OF RaisecomCPUHistoryEntry
				   ACCESS   not-accessible
				   STATUS   current
				   DESCRIPTION
				            "This table contains CPU hsitory utilization records."
				   ::= { raisecomCPUUtilizationGroup 2 } 
				   
       raisecomCPUHistoryEntry OBJECT-TYPE
				    SYNTAX  RaisecomCPUHistoryEntry
				    ACCESS  not-accessible
				    STATUS  current
				    DESCRIPTION
				            "CPU history utilization record."
				    INDEX           { raisecomCPUHistoryPeriod, raisecomProcessIndex } 
				    ::= { raisecomCPUHistoryTable 1 }  
				    
       RaisecomCPUHistoryEntry ::= SEQUENCE {
       				raisecomCPUHistoryPeriod     INTEGER,
			        raisecomCPUHistoryIndex      INTEGER,
			        raisecomCPUHistoryTotalUtil  INTEGER			          		
			        } 

	   raisecomCPUHistoryPeriod OBJECT-TYPE
					SYNTAX	INTEGER {
										fiveSec(1), 
										oneMin(2),
										tenMin(3),
										twoHour(4)
									}				    
					ACCESS  not-accessible
					STATUS  current
					DESCRIPTION
					"Periods for computing CPU history utilization, the first index of CPU history utilization table."
					::= { raisecomCPUHistoryEntry 1 }     
	
	   raisecomCPUHistoryIndex OBJECT-TYPE
					SYNTAX	INTEGER 				    
					ACCESS  not-accessible
					STATUS  current
					DESCRIPTION
					"Process sequence number,the second index of CPU history utilization table."
					::= { raisecomCPUHistoryEntry 2 }
	
	   raisecomCPUHistoryTotalUtil OBJECT-TYPE
					SYNTAX	INTEGER (0..100)
					UNITS	"percent" 				    
					ACCESS  read-only
					STATUS  current
					DESCRIPTION
					"History record of CPU utilization in the specified period. "
					::= { raisecomCPUHistoryEntry 3 }
	
--------------------------------------------------------------------------
--raisecomCPUProcessesGroup
--------------------------------------------------------------------------   

       raisecomCPUProcessesGroup  OBJECT IDENTIFIER
                   ::= { raisecomCPUTableGroup 2 }

---------------------------------
--raisecomProcessesTable 
--------------------------------- 
       raisecomProcessesTable OBJECT-TYPE
				   SYNTAX   SEQUENCE OF RaisecomProcessesEntry
				   ACCESS   not-accessible
				   STATUS   current
				   DESCRIPTION
				            "This table contains information about processes."
				   ::= { raisecomCPUProcessesGroup 1 } 
				   
       raisecomProcessesEntry OBJECT-TYPE
				    SYNTAX  RaisecomProcessesEntry
				    ACCESS  not-accessible
				    STATUS  current
				    DESCRIPTION
				            "Information about processes."
				    INDEX           { raisecomProcessIndex } 
				    ::= { raisecomProcessesTable 1 }  
				    
       RaisecomProcessesEntry ::= SEQUENCE {
			        raisecomProcessIndex            INTEGER,
			        raisecomProcessPID              INTEGER,
			        raisecomProcessName             OCTET STRING,
			        raisecomProcessRunTimeTotal     CPUTimeStamp,
			        raisecomProcessInvokedTotal	    INTEGER,
			        raisecomProcessTimeCreated      TimeStamp,
			        raisecomProcessNormalPriority   INTEGER,
			        raisecomProcessCurrentPriority  INTEGER,
			        raisecomProcessStatus           ProcessStatus,
			        raisecomProcessErrorNo          INTEGER,
			        raisecomProcessStackSize        INTEGER,
			        raisecomProcessStackCurrentSize INTEGER,
			        raisecomProcessStackMaxSize     INTEGER,
			        raisecomProcessStackBegin       INTEGER,
			        raisecomProcessStackPointer     INTEGER,
			        raisecomProcessStackEnd         INTEGER,
			        raisecomProcessProgramCounter   INTEGER,
			        raisecomProcessEntry            INTEGER,
			        raisecomProcessSemWait          INTEGER,
			        raisecomProcessDelay			INTEGER       		
			        } 
			         
       raisecomProcessIndex OBJECT-TYPE
					SYNTAX  INTEGER 				    
					ACCESS  read-only
					STATUS  current
					DESCRIPTION
					"This object index of processes table."
					::= { raisecomProcessesEntry 1 }  
        
       raisecomProcessPID OBJECT-TYPE
					SYNTAX  INTEGER 				    
					ACCESS  read-only
					STATUS  current
					DESCRIPTION
					"This object contains the process ID."
					::= { raisecomProcessesEntry 2 } 
					
	   raisecomProcessName OBJECT-TYPE
					SYNTAX  OCTET STRING (SIZE(1..32))  				    
					ACCESS  read-only					
					STATUS  current
					DESCRIPTION
					"The name associated with this process."
					::= { raisecomProcessesEntry 3 } 			
					
	   raisecomProcessRunTimeTotal OBJECT-TYPE
					SYNTAX  CPUTimeStamp  				    
					ACCESS  read-only
					STATUS  current
					DESCRIPTION
					"The amount of time the process occupied, in microseconds."
					::= { raisecomProcessesEntry 4 } 
	
	   raisecomProcessInvokedTotal OBJECT-TYPE
					SYNTAX  INTEGER  				    
					ACCESS  read-only
					STATUS  current
					DESCRIPTION
					"The number of times since raisecomProcessTimeCreated 
					that the process has been invoked."
					::= { raisecomProcessesEntry 5 }
	
	   raisecomProcessTimeCreated OBJECT-TYPE
					SYNTAX  TimeStamp  				    
					ACCESS  read-only
					STATUS  current
					DESCRIPTION
					"The time when the process was created. 
					The process sequence number and the time 
					when the process was created, uniquely identifies a process."
					::= { raisecomProcessesEntry 6 }
	
	   raisecomProcessNormalPriority OBJECT-TYPE
					SYNTAX  INTEGER  				    
					ACCESS  read-only
					STATUS  current
					DESCRIPTION
					"The normal priority at which the process is running."
					::= { raisecomProcessesEntry 7 }     
					
	   raisecomProcessCurrentPriority OBJECT-TYPE
					SYNTAX  INTEGER  				    
					ACCESS  read-only
					STATUS  current
					DESCRIPTION
					"The current priority at which the process is running."
					::= { raisecomProcessesEntry 8 }			
					
	   raisecomProcessStatus OBJECT-TYPE
					SYNTAX  ProcessStatus  				    
					ACCESS  read-only
					STATUS  current
					DESCRIPTION
					"The current status of the process."
					::= { raisecomProcessesEntry 9 }				
					
	   raisecomProcessErrorNo OBJECT-TYPE
					SYNTAX  INTEGER  				    
					ACCESS  read-only
					STATUS  current
					DESCRIPTION
					"Error number of the process."
					::= { raisecomProcessesEntry 10 }			
					
       raisecomProcessStackSize OBJECT-TYPE
					SYNTAX  INTEGER  				    
					ACCESS  read-only
					STATUS  current
					DESCRIPTION
					"Stack size specified for the process."
					::= { raisecomProcessesEntry 11 }			
		
	   raisecomProcessStackCurrentSize OBJECT-TYPE
					SYNTAX  INTEGER  				    
					ACCESS  read-only
					STATUS  current
					DESCRIPTION
					"Stack size for the process current using."
					::= { raisecomProcessesEntry 12 }
		
	   raisecomProcessStackMaxSize OBJECT-TYPE
					SYNTAX  INTEGER  				    
					ACCESS  read-only
					STATUS  current
					DESCRIPTION
					"Stack max size for the process used."
					::= { raisecomProcessesEntry 13 }	
		
	   raisecomProcessStackBegin OBJECT-TYPE
					SYNTAX  INTEGER  				    
					ACCESS  read-only
					STATUS  current
					DESCRIPTION
					"Start position of the specified stack for the process."
					::= { raisecomProcessesEntry 14 }
		
	   raisecomProcessStackPointer OBJECT-TYPE
					SYNTAX  INTEGER  				    
					ACCESS  read-only
					STATUS  current
					DESCRIPTION
					"Current position of the process stack pointer."
					::= { raisecomProcessesEntry 15 }

	   raisecomProcessStackEnd OBJECT-TYPE
					SYNTAX  INTEGER  				    
					ACCESS  read-only
					STATUS  current
					DESCRIPTION
					"End position of the specified stack for the process."
					::= { raisecomProcessesEntry 16 }
								
	   raisecomProcessProgramCounter OBJECT-TYPE
					SYNTAX  INTEGER  				    
					ACCESS  read-only
					STATUS  current
					DESCRIPTION
					"The program counter of the process."
					::= { raisecomProcessesEntry 17 }	
		
	   raisecomProcessEntry OBJECT-TYPE
					SYNTAX  INTEGER  				    
					ACCESS  read-only
					STATUS  current
					DESCRIPTION
					"The entry of the process."
					::= { raisecomProcessesEntry 18 }	
							
	   raisecomProcessSemWait OBJECT-TYPE
					SYNTAX  INTEGER  				    
					ACCESS  read-only
					STATUS  current
					DESCRIPTION
					"The semaphore of the process waiting for."
					::= { raisecomProcessesEntry 19 }			
					
	   raisecomProcessDelay OBJECT-TYPE
					SYNTAX  INTEGER  				    
					ACCESS  read-only
					STATUS  current
					DESCRIPTION
					"Time of the process delay."
					::= { raisecomProcessesEntry 20 }			
										
---------------------------------
--raisecomProcessStatisticsTable 
--------------------------------- 
       raisecomProcessStatisticsTable OBJECT-TYPE
				   SYNTAX   SEQUENCE OF RaisecomProcessStatisticsEntry
				   ACCESS   not-accessible
				   STATUS   current
				   DESCRIPTION
				            "This table contains statistics information for processes.
				            The first index is raisecomProcessIndex,
				            the second index is raisecomProcessStatisticsPeriod"
				   ::= { raisecomCPUProcessesGroup 2 } 
				   
       raisecomProcessStatisticsEntry OBJECT-TYPE
				    SYNTAX  RaisecomProcessStatisticsEntry
				    ACCESS  not-accessible
				    STATUS  current
				    DESCRIPTION
				            "Statistics information for processes."
				    INDEX           { raisecomProcessIndex, raisecomProcessStatisticsPeriod } 
				    ::= { raisecomProcessStatisticsTable 1 }  
				    
       RaisecomProcessStatisticsEntry ::= SEQUENCE {
			        raisecomProcessStatisticsPeriod    INTEGER,
			        raisecomProcessRunTime             CPUTimeStamp,
			        raisecomProcessInvoked             INTEGER,
			        raisecomProcessUtilization         INTEGER			          		
			        } 
							
	   raisecomProcessStatisticsPeriod OBJECT-TYPE
					SYNTAX	INTEGER {
										fiveSec(1),
							            oneMin(2),
										tenMin(3)									
									}  				    
					ACCESS  not-accessible
					STATUS  current
					DESCRIPTION
					"Periods for process statistics,
					the second index of process statistics table."
					::= { raisecomProcessStatisticsEntry 1 }				
	
	   raisecomProcessRunTime OBJECT-TYPE
					SYNTAX	CPUTimeStamp 				    
					ACCESS  read-only
					STATUS  current
					DESCRIPTION
					"Time of the process occupied in the specified period."
					::= { raisecomProcessStatisticsEntry 2 }
	
	   raisecomProcessInvoked OBJECT-TYPE
					SYNTAX	INTEGER 				    
					ACCESS  read-only
					STATUS  current
					DESCRIPTION
					"Times of the process invoked in the specified period."
					::= { raisecomProcessStatisticsEntry 3 }
	
	   raisecomProcessUtilization OBJECT-TYPE
					SYNTAX	INTEGER (0..100)
					UNITS	"percent" 				    
					ACCESS  read-only
					STATUS  current
					DESCRIPTION
					"This object provides a general idea of how busy 
					a process caused the processor to be over a specified period."
					::= { raisecomProcessStatisticsEntry 4 }	
	
---------------------------------
--raisecomDeadProcessesTable  
--------------------------------- 
       raisecomDeadProcessesTable OBJECT-TYPE
				   SYNTAX   SEQUENCE OF RaisecomDeadProcessesEntry
				   ACCESS   not-accessible
				   STATUS   current
				   DESCRIPTION
				            "This table contains dead processes information."
				   ::= { raisecomCPUProcessesGroup 3 } 
				   
       raisecomDeadProcessesEntry OBJECT-TYPE
				    SYNTAX  RaisecomDeadProcessesEntry
				    ACCESS  not-accessible
				    STATUS  current
				    DESCRIPTION
				            "Dead processes information."
				    INDEX           { raisecomDeadProcessIndex } 
				    ::= { raisecomDeadProcessesTable 1 }  
				    
       RaisecomDeadProcessesEntry ::= SEQUENCE {
			        raisecomDeadProcessIndex        INTEGER,
			        raisecomDeadProcessName         OCTET STRING,
			        raisecomDeadProcessEntry        INTEGER,
			        raisecomDeadProcessErrorNo      INTEGER,
			        raisecomDeadProcessPriority     INTEGER,
			        raisecomDeadProcessMaxStackSize INTEGER,
			        raisecomDeadProcessTimeDelete   TimeStamp,
			        raisecomDeadProcessDeadTimes    INTEGER,
			        raisecomDeadProcessStatus       ProcessStatus			          		
			        } 
	
	   raisecomDeadProcessIndex OBJECT-TYPE
					SYNTAX	INTEGER 				    
					ACCESS  not-accessible
					STATUS  current
					DESCRIPTION
					"Process sequence number,the index of dead processes table."
					::= { raisecomDeadProcessesEntry 1 }
	
       raisecomDeadProcessName OBJECT-TYPE
					SYNTAX	OCTET STRING (SIZE(1..32)) 				    
					ACCESS  read-only
					STATUS  current
					DESCRIPTION
					"The name associated with this dead process."
					::= { raisecomDeadProcessesEntry 2 }

       raisecomDeadProcessEntry OBJECT-TYPE
					SYNTAX	INTEGER 				    
					ACCESS  read-only
					STATUS  current
					DESCRIPTION
					"The entry of the dead process."
					::= { raisecomDeadProcessesEntry 3 }

       raisecomDeadProcessErrorNo OBJECT-TYPE
					SYNTAX	INTEGER 				    
					ACCESS  read-only
					STATUS  current
					DESCRIPTION
					"Error number of the dead process."
					::= { raisecomDeadProcessesEntry 4 }

       raisecomDeadProcessPriority OBJECT-TYPE
					SYNTAX	INTEGER 				    
					ACCESS  read-only
					STATUS  current
					DESCRIPTION
					"The priority at which the dead process."
					::= { raisecomDeadProcessesEntry 5 }

       raisecomDeadProcessMaxStackSize OBJECT-TYPE
					SYNTAX	INTEGER 				    
					ACCESS  read-only
					STATUS  current
					DESCRIPTION
					"Max stack size for the dead process used."
					::= { raisecomDeadProcessesEntry 6 }  
					
	   raisecomDeadProcessTimeDelete OBJECT-TYPE
					SYNTAX	TimeStamp 				    
					ACCESS  read-only
					STATUS  current
					DESCRIPTION
					"The time when the process was deleted."
					::= { raisecomDeadProcessesEntry 7 }
					
	   raisecomDeadProcessDeadTimes OBJECT-TYPE
					SYNTAX	INTEGER 				    
					ACCESS  read-only
					STATUS  current
					DESCRIPTION
					"Times of the process dead."
					::= { raisecomDeadProcessesEntry 8 }    
					
	   raisecomDeadProcessStatus OBJECT-TYPE
					SYNTAX	ProcessStatus 				    
					ACCESS  read-only
					STATUS  current
					DESCRIPTION
					"The status of the dead process, dead or restart."
					::= { raisecomDeadProcessesEntry 9 }
 					
--
-- RAISECOM END Pool objects
--
	
	raisecomEndPool MODULE-IDENTITY
                LAST-UPDATED 	"200412170000Z"
                ORGANIZATION 	"RAISECOM TECH, Ltd."
                CONTACT-INFO 	"www.raisecom.com"
                DESCRIPTION  	
                		"raisecom System objects: objects common to all platforms."
        	::= { raisecomSystem 2 }
		
	raisecomEndPoolTable OBJECT-TYPE
	        SYNTAX      SEQUENCE OF RaisecomEndPoolEntry
	        MAX-ACCESS  not-accessible
	        STATUS      current
	        DESCRIPTION
	                "A table of drivers Pool on a managed system."
	        ::= { raisecomEndPool 1 }
	
	raisecomEndPoolEntry OBJECT-TYPE
	        SYNTAX      RaisecomEndPoolEntry
	        MAX-ACCESS  not-accessible
	        STATUS      current
	        DESCRIPTION
	                "An entry in the END driver Pool monitoring table."
	        INDEX       { raisecomBasePort }
	        ::= { raisecomEndPoolTable 1 }
	
	RaisecomEndPoolEntry ::=
	        SEQUENCE {
	                raisecomBasePort       	INTEGER,
	                raisecomTotalEndPool 	INTEGER,
	                raisecomFreeEndPool	INTEGER
	        }
		
	
	raisecomBasePort OBJECT-TYPE
	        SYNTAX  INTEGER 
	        MAX-ACCESS  not-accessible
	        STATUS  current
	        DESCRIPTION
	                "The port number based 1 of the port for which this entry
	                contains bridge management information."
   		    ::= {  raisecomEndPoolEntry 1 }
	
	raisecomTotalEndPool OBJECT-TYPE
	        SYNTAX      INTEGER
	        MAX-ACCESS  read-only
	        STATUS      current
	        DESCRIPTION
	                "Indicates the number of mBlks pre-allocated for this END driver."
	        ::= { raisecomEndPoolEntry 2 }

	raisecomFreeEndPool OBJECT-TYPE
	        SYNTAX      INTEGER
	        MAX-ACCESS  read-only
	        STATUS      current
	        DESCRIPTION
	                "Indicates the number of mBlks available  in  this END driver pool."
	        ::= { raisecomEndPoolEntry 3 }    
	        
--
-- RAISECOM Memory objects
--                
	 raisecomMemory MODULE-IDENTITY
                LAST-UPDATED 	"200412170000Z"
                ORGANIZATION 	"RAISECOM TECH, Ltd."
                CONTACT-INFO 	"www.raisecom.com"
                DESCRIPTION  	
                		"raisecom System objects: memory objects."	
      ::= { raisecomSystem 3 }   
            
     raisecomTotalMemory OBJECT-TYPE
	        SYNTAX INTEGER
	        UNITS        "Byte"
			MAX-ACCESS read-only
	        STATUS current
	        DESCRIPTION
	          "The  total memory of the system as reported by the
	  	   operating system."
	::= { raisecomMemory 1 }
	
	raisecomAvailableMemory OBJECT-TYPE
	        SYNTAX INTEGER
	        UNITS        "Byte"
			MAX-ACCESS read-only
	        STATUS current
	        DESCRIPTION
	          "The available total memory of the system as reported by the
	  	   operating system."
	::= { raisecomMemory 2}

    raisecomMaxUtilmemory OBJECT-TYPE
            SYNTAX INTEGER
            UNITS        "percent"
        	MAX-ACCESS read-only
            STATUS current
            DESCRIPTION
                  "The maximum memory utilization by this system since
		   system starting. This value may be cleared."
	::= { raisecomMemory 3 }    
	
--
-- RAISECOM Information objects
--                

		 raisecomInformation MODULE-IDENTITY
                LAST-UPDATED 	"200507270000Z"
                ORGANIZATION 	"RAISECOM TECH, Ltd."
                CONTACT-INFO 	"www.raisecom.com"
                DESCRIPTION  	
                		"raisecom System objects: objects common to all platforms."
 		   		::= { raisecomSystem 4 }
 
		    raisecomDeviceType OBJECT-TYPE
		            SYNTAX  OCTET STRING
		           	MAX-ACCESS read-only
		            STATUS current
		            DESCRIPTION
		                  "Device type."
					::= { raisecomInformation 1 }   
					 
			--Temperature group	
		    raisecomTemperature    OBJECT IDENTIFIER ::= { raisecomInformation 2 }
		    
		       raisecomTemperatureValue OBJECT-TYPE
		               SYNTAX      INTEGER 
		               UNITS  	   "Celsius "
                       MAX-ACCESS  read-only
                       STATUS      current
                       DESCRIPTION  
                       		"The current temperature of the device."
        		  	   ::= { raisecomTemperature 1 }   
        		  	   
        	   raisecomTemperatureMin OBJECT-TYPE
       	               SYNTAX      INTEGER 
       	               UNITS  	   "Celsius "
                       MAX-ACCESS  read-only
                       STATUS      current
                       DESCRIPTION  
                       		"The minimum temperature that has occured."
        		  	   ::= { raisecomTemperature 2 }   
        	   
        	   raisecomTemperatureMax OBJECT-TYPE
       	               SYNTAX      INTEGER  
       	               UNITS  	   "Celsius "
                       MAX-ACCESS  read-only
                       STATUS      current
                       DESCRIPTION  
                       		"The maximum temperature that has occured."
        		  	   ::= { raisecomTemperature 3 }   
                                        
               raisecomTemperatureTrapEnable   OBJECT-TYPE
 	                   SYNTAX     EnableVar
        			   MAX-ACCESS read-write
                       STATUS     current
                       DESCRIPTION 
                            " Indicates whether the temperature trap is enabled."                                   
 	                   ::= { raisecomTemperature 4 }
 	   
               raisecomTemperatureThresholdLow  OBJECT-TYPE
       	               SYNTAX      INTEGER(0..30)
       	               UNITS  	   "Celsius " 
                       MAX-ACCESS  read-write
                       STATUS      current
                       DESCRIPTION  
                       		"Low threshold of the temperature trap."
        		  	   ::= { raisecomTemperature 5 }    

               raisecomTemperatureThresholdHigh  OBJECT-TYPE
       	               SYNTAX      INTEGER(30..70)   
       	               UNITS  	   "Celsius "
                       MAX-ACCESS  read-write
                       STATUS      current
                       DESCRIPTION  
                       		"High threshold of the temperature trap."
        		  	   ::= { raisecomTemperature 6 }     
        		  	   
        	   raisecomTemperatureTrapTimes   OBJECT-TYPE
		               SYNTAX      INTEGER
                       MAX-ACCESS  read-only
                       STATUS      current
                       DESCRIPTION  
                       		"How many times abnormal temperature has occured."
        		  	   ::= { raisecomTemperature 7 }
  
        	
        	--Vlot  Information
        	raisecomVolt    OBJECT IDENTIFIER ::= { raisecomInformation 3 }
        		  	   
        	raisecomVoltTable OBJECT-TYPE
					SYNTAX		SEQUENCE OF	RaisecomVoltEntry
					MAX-ACCESS	not-accessible
					STATUS		current
					DESCRIPTION
						 "A table of device vlot and associated properties.."
					::=	{  raisecomVolt 1 } 
				
				raisecomVoltEntry  OBJECT-TYPE
						SYNTAX		RaisecomVoltEntry
						MAX-ACCESS	not-accessible
						STATUS		current
						DESCRIPTION
						   	"Table entry for device vlot."
						INDEX {	raisecomVoltIndex }
						::=	{ raisecomVoltTable 1 } 	  
						            
			    RaisecomVoltEntry ::= SEQUENCE {
			        raisecomVoltIndex         	INTEGER,
			        raisecomVoltReference     	INTEGER,
			        raisecomVoltValue      	  	INTEGER,
			        raisecomVoltMin    		  	INTEGER,
			        raisecomVoltMax           	INTEGER,
			        raisecomVoltTrapEnable    	EnableVar,
			        raisecomVoltThresholdLow    INTEGER,
			        raisecomVoltThresholdHigh   INTEGER,
			        raisecomVoltTrapTimes       INTEGER
				    }
				
			    raisecomVoltIndex OBJECT-TYPE
						SYNTAX		INTEGER
						MAX-ACCESS	read-only
						STATUS		current
						DESCRIPTION
							"An index based 1 that uniquely identifies a volt entry."
						::=	{ raisecomVoltEntry 1 }
				
				raisecomVoltReference OBJECT-TYPE
		               SYNTAX      INTEGER   
		               UNITS  	   "mV"
                       MAX-ACCESS  read-only
                       STATUS      current    
                       DESCRIPTION  
                       		"The reference volt."
        		  	   ::= { raisecomVoltEntry 2 }    
        		  	   
        		raisecomVoltValue   OBJECT-TYPE
		               SYNTAX      INTEGER
		               UNITS  	   "mV" 
                       MAX-ACCESS  read-only
                       STATUS      current
                       DESCRIPTION  
                       		"The current value."
        		  	   ::= { raisecomVoltEntry 3 } 
        		  	   
        		raisecomVoltMin     OBJECT-TYPE
		               SYNTAX      INTEGER
		               UNITS  	   "mV" 
                       MAX-ACCESS  read-only
                       STATUS      current
                       DESCRIPTION  
                       		"The minimum value that has occured."
        		  	   ::= { raisecomVoltEntry 4 }
				
                raisecomVoltMax    OBJECT-TYPE
		               SYNTAX      INTEGER
		               UNITS  	   "mV" 
                       MAX-ACCESS  read-only
                       STATUS      current
                       DESCRIPTION  
                       		"The maximum value that has occured."
        		  	   ::= { raisecomVoltEntry 5 }    
        		 
        		raisecomVoltTrapEnable  OBJECT-TYPE
 	                   SYNTAX     EnableVar
        			   MAX-ACCESS read-write
                       STATUS     current
                       DESCRIPTION 
                            " Indicates whether the volt trap is enabled."                                   
 	                   ::= { raisecomVoltEntry 6 }   
 	                   
 	            raisecomVoltThresholdLow  OBJECT-TYPE
       	               SYNTAX      INTEGER(3000..3300)
       	               UNITS  	   "mV" 
                       MAX-ACCESS  read-write
                       STATUS      current
                       DESCRIPTION  
                       		"The low threshold of the volt trap."
        		  	   ::= { raisecomVoltEntry 7 } 

               raisecomVoltThresholdHigh  OBJECT-TYPE
       	               SYNTAX      INTEGER(3300..3600)
       	               UNITS  	   "mV" 
                       MAX-ACCESS  read-write
                       STATUS      current
                       DESCRIPTION  
                       		"The high threshold of the volt trap."
        		  	   ::= { raisecomVoltEntry 8 }

                raisecomVoltTrapTimes   OBJECT-TYPE
		               SYNTAX      INTEGER
                       MAX-ACCESS  read-only
                       STATUS      current
                       DESCRIPTION  
                       		"How many times abnormal volt has occured."
        		  	   ::= { raisecomVoltEntry 9 }
          	
          	--Device information trap  
        	raisecomInformationTrap    OBJECT IDENTIFIER ::= { raisecomInformation 4 }
        	
        		 temperatureAbnormalTrap    NOTIFICATION-TYPE
				         OBJECTS { raisecomTemperatureValue }
				         STATUS  current
				         DESCRIPTION
				               "Current temperature of the device is abnormal."
       					 ::= { raisecomInformationTrap 1 }
                 
                 temperatureNormalTrap    NOTIFICATION-TYPE
				         OBJECTS { raisecomTemperatureValue }
				         STATUS  current
				         DESCRIPTION
				               "Current temperature of the device return to normal."
       					 ::= { raisecomInformationTrap 2 }
                 
                 raisecomVoltAbnormalTrap    NOTIFICATION-TYPE
				         OBJECTS { raisecomVoltIndex, raisecomVoltReference, raisecomVoltValue }
				         STATUS  current
				         DESCRIPTION
				               "Current volt of the device is abnormal."
       					 ::= { raisecomInformationTrap 3 }

                 raisecomVoltNormalTrap    NOTIFICATION-TYPE
				         OBJECTS { raisecomVoltIndex, raisecomVoltReference, raisecomVoltValue }
				         STATUS  current
				         DESCRIPTION
				               "Current volt of the device return to normal."
       					 ::= { raisecomInformationTrap 4 }

                 raisecomPowerTrap    NOTIFICATION-TYPE
				         STATUS  current
				         DESCRIPTION
				               "Power down trap."
       					 ::= { raisecomInformationTrap 5 }

        		 raisecomDualPowerTrap    NOTIFICATION-TYPE
				         --OBJECTS { raisecomAlarmHistStatus, raisecomAlarmHistSource,raisecomAlarmHistDescr, raisecomAlarmHistTimestamp, raisecomAlarmHistType }
				         OBJECTS { raisecomPowerStatus }
				         STATUS  current
				         DESCRIPTION
				               "A raisecomPowerTrap trap is sent when a power alarm generate."				               
       					 ::= { raisecomInformationTrap 6 }
       					 

			--Power group
        	raisecomPower    OBJECT IDENTIFIER ::= { raisecomInformation 5}

                 raisecomPowerTrapEnable    OBJECT-TYPE
				         SYNTAX      EnableVar
				         MAX-ACCESS  read-write
				         STATUS      current
				         DESCRIPTION  
				               "Indicates whether the power down trap is enabled."
				         ::= { raisecomPower 1 }

		    raisecomPowerAlarm    OBJECT IDENTIFIER ::= { raisecomInformation 6 }
		    
		        raisecomPowerOnOffTrapEnable OBJECT-TYPE
 	                   SYNTAX     EnableVar
        			   MAX-ACCESS read-write
                       STATUS     current
                       DESCRIPTION 
                            " Indicates whether the power alarm trap is enabled." 
                       DEFVAL { enable}                                  
 	                   ::= { raisecomPowerAlarm 1 }
		    
        	   raisecomPowerOneTimes   OBJECT-TYPE
		               SYNTAX      INTEGER
                       MAX-ACCESS  read-only
                       STATUS      current
                       DESCRIPTION  
                       		"How many times power one alarm has occured."
        		  	   ::= { raisecomPowerAlarm 2 }   

        	   raisecomPowerTwoTimes   OBJECT-TYPE
		               SYNTAX      INTEGER
                       MAX-ACCESS  read-only
                       STATUS      current
                       DESCRIPTION  
                       		"How many times power two alarm has occured."
        		  	   ::= { raisecomPowerAlarm 3 }   
        		  	   
				raisecomPowerStatus OBJECT-TYPE
		               SYNTAX INTEGER { 
		                           dual_power_on(1),
		                           dual_power_off(2),
		                           power1_off(3),
		                           power2_off(4)
		                           }  
                       MAX-ACCESS  read-only
                       STATUS      current    
                       DESCRIPTION  
                       		"The status of power alarm."
        		  	   ::= { raisecomPowerAlarm 4 } 
			--fan group
      raisecomFan    OBJECT IDENTIFIER ::= { raisecomInformation 7}

		       raisecomFanSpeedDueValue OBJECT-TYPE
		            SYNTAX  INTEGER
		           	MAX-ACCESS read-only
		            STATUS current
		            DESCRIPTION
		            "Deu to fan speed."
					      ::= { raisecomFan 1 }  
					 
					 --statistic table---    
           raisecomFanSpeedValueTable  OBJECT-TYPE 
                SYNTAX   SEQUENCE OF raisecomFanSpeedValueEntry
                ACCESS	 not-accessible
                STATUS   current
                DESCRIPTION
                "This table provides objects to fan speed list"
                ::= { raisecomFan 2 } 
                
           raisecomFanSpeedValueEntry  OBJECT-TYPE
                SYNTAX   raisecomFanSpeedValueEntry
                ACCESS   not-accessible
                STATUS   current
                DESCRIPTION
                "An entry in raisecomFanSpeedValueTable"   
                INDEX { raisecomFanIndex }
                ::= { raisecomFanSpeedValueTable 1 } 
                
           raisecomFanSpeedValueEntry ::= SEQUENCE {
              raisecomFanIndex             INTEGER,
	           	raisecomFanSpeedValue        INTEGER
           }

           raisecomFanIndex  OBJECT-TYPE
           		SYNTAX	INTEGER
           		ACCESS	not-accessible
           		STATUS	current
	           	DESCRIPTION
		    	    "Index of fan, range(1...fannumber)" 
           		::= { raisecomFanSpeedValueEntry 1 }

           raisecomFanSpeedValue  OBJECT-TYPE
           		SYNTAX	INTEGER
           		ACCESS	read-only
           		STATUS	current
	           	DESCRIPTION
		    	    "speed of fan" 
           		::= { raisecomFanSpeedValueEntry 2 }	           
				         
END
