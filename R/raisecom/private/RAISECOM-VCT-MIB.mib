--MibName=raisecomVct
-- *****************************************************************
-- RAISECOM-VCT-MIB.my
--
-- May 2006, zhangjun
--
-- Copyright(c) 2003-2005 by RAISECOM TECH, Ltd. 
-- All rights reserved.
-- *****************************************************************


RAISECOM-VCT-MIB DEFINITIONS ::= BEGIN

IMPORTS
    MODULE-IDENTITY,
    OBJECT-TYPE                         
    									FROM SNMPv2-SMI
		ifIndex          	
											FROM IF-MIB
    raisecomAgent                       
    									FROM RAISECOM-BASE-MIB;

raisecomVct MODULE-IDENTITY
    LAST-UPDATED   "200609080000Z"
    ORGANIZATION   "Raisecom, Inc."
    CONTACT-INFO  
                "       Raise Systems
                        
                Postal: Beijing,
                        China

                   Tel: 86-010-82884499

                E-mail: zhangjun@raisecom.com"
    DESCRIPTION
        "This MIB module defines objects to VCT "
        REVISION   "200609080000Z"
        DESCRIPTION
            "The initial revision of this MIB."
        ::={ raisecomAgent 14 }




-- MIB Object Definitions

raisecomVctPortObjects        OBJECT IDENTIFIER ::=
                                        {raisecomVct 1 }



-- raisecomVCTPortTable

raisecomVctPortTable OBJECT-TYPE
    SYNTAX      SEQUENCE OF RaisecomVctPortEntry
    MAX-ACCESS  not-accessible
    STATUS      current
    DESCRIPTION
        "This table provides objects to VCT port list. "
    ::={ raisecomVctPortObjects 1 }

raisecomVctPortEntry OBJECT-TYPE
    SYNTAX      RaisecomVctPortEntry
    MAX-ACCESS  not-accessible
    STATUS      current
    DESCRIPTION
        "An entry in the raisecomVctTable provides objects show VCT parameter.
        "
    INDEX        { ifIndex }
    ::={ raisecomVctPortTable 1 }


RaisecomVctPortEntry ::= SEQUENCE {
		raisecomVctPortAttribute        INTEGER,
		raisecomVctPortIssuedTime	OCTET STRING,
		raisecomVctPortCableTXStatus	INTEGER,
		raisecomVctPortCableTXLength	INTEGER,
		raisecomVctPortCableRXStatus	INTEGER,
		raisecomVctPortCableRXLength	INTEGER
}


raisecomVctPortAttribute OBJECT-TYPE
		SYNTAX	INTEGER{unSupported(1), neverIssued(2), issued(3) , testing(4) }
		ACCESS	read-only
		STATUS	current
		DESCRIPTION
			"Specifies VCT attribute of the testing port"
		::= { raisecomVctPortEntry 1 }

raisecomVctPortIssuedTime OBJECT-TYPE
		SYNTAX	OCTET STRING(SIZE(1..32))
		ACCESS	read-only
		STATUS	current
		DESCRIPTION
			"Specifies VCT issued time of the testing port"
		::= { raisecomVctPortEntry 2 }
		
raisecomVctPortCableTXStatus OBJECT-TYPE
		SYNTAX	INTEGER{normal(1), open(2), shorted(3), error(4), invalidation(5)}
		ACCESS	read-only
		STATUS	current
		DESCRIPTION
			"Specifies VCT resault of the cable TX pair"
		::= { raisecomVctPortEntry 3 }

raisecomVctPortCableTXLength OBJECT-TYPE
		SYNTAX	INTEGER
		ACCESS	read-only
		STATUS	current
		DESCRIPTION
			"Specifies error port of the cable TX pair"
		::= { raisecomVctPortEntry 4 }
		
raisecomVctPortCableRXStatus OBJECT-TYPE
		SYNTAX	INTEGER{normal(1), open(2), shorted(3), error(4), invalidation(5)}
		ACCESS	read-only
		STATUS	current
		DESCRIPTION
			"Specifies VCT resault of the cable RX pair"
		::= { raisecomVctPortEntry 5 }

raisecomVctPortCableRXLength OBJECT-TYPE
		SYNTAX	INTEGER
		ACCESS	read-only
		STATUS	current
		DESCRIPTION
			"Specifies error port of the cable RX pair"
		::= { raisecomVctPortEntry 6 }
		
		
raisecomVctPortStartTest OBJECT-TYPE
    SYNTAX      INTEGER
    MAX-ACCESS  read-write
    STATUS      current
    DESCRIPTION
        "specifies that which port is going to be tested."
    ::={ raisecomVctPortObjects 2 }

END
