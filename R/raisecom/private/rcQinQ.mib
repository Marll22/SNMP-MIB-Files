--MibName=rcQinQ
-- *****************************************************************
-- RAISECOM-QINQ-MIB.mib:   Raisecom QinQ MIB file 
--
-- Copyright (c) 1994-2004 by Raisecom, Inc.
-- All rights reserved.
--
-- *****************************************************************
RAISECOM-QINQ-MIB  DEFINITIONS ::= BEGIN

IMPORTS
        iscomSwitch                       FROM RAISECOM-BASE-MIB
        RowStatus                         FROM SNMPv2-TC
        Vlanset, EnableVar                FROM SWITCH-TC
        rcPortIndex          		      FROM SWITCH-SYSTEM-MIB;
 
rcQinQ             OBJECT IDENTIFIER ::= { iscomSwitch 42 }

rcQinQCfg          MODULE-IDENTITY
    LAST-UPDATED   "200901190000Z"
    ORGANIZATION   "Raisecom, Inc."
    CONTACT-INFO  
                "       Raise Systems
                        
                Postal: Beijing,
                        China

                   Tel: 86-010-82884499

                E-mail: wangjing_rj@raisecom.com"
    DESCRIPTION
        "This MIB module defines objects to QinQ "
        REVISION   "200901190000Z"
        DESCRIPTION
            "The initial revision of this MIB."
        ::={ rcQinQ 1 } 

-- -------------------------------------------------------------
-- groups in the rcQinQ MIB     rcQinQDot1q
-- -------------------------------------------------------------
rcQinQDot1q                   OBJECT IDENTIFIER ::= { rcQinQCfg 1 }

rcQinQDtOuterTpid             OBJECT-TYPE
        SYNTAX INTEGER (0..65535)
        MAX-ACCESS read-write
        STATUS current
        DESCRIPTION
            "TPID of outer tag."
        ::= { rcQinQDot1q 1 }

rcQinQPortTable               OBJECT-TYPE
        SYNTAX      SEQUENCE OF RcQinQPortEntry
        MAX-ACCESS  not-accessible
        STATUS      current
        DESCRIPTION
            "QinQ port table"
        ::= { rcQinQDot1q 2 }

rcQinQPortEntry               OBJECT-TYPE
        SYNTAX      RcQinQPortEntry
        MAX-ACCESS  not-accessible
        STATUS      current
        DESCRIPTION
            "An entry in the rcQinQPortTable. It contains
            QinQ status in each interface port."
	    INDEX        { rcPortIndex }    
        ::={ rcQinQPortTable 1 }
    
        RcQinQPortEntry ::= SEQUENCE
        {
    	    rcQinQStatus	   INTEGER	
        }

rcQinQStatus             OBJECT-TYPE
        SYNTAX INTEGER  {
                 none(1),
                 dot1q-tunnel(2),
                 double-tagging(3)
                 }
        MAX-ACCESS read-write
        STATUS current
        DESCRIPTION
            "Port QinQ mode."
        ::= { rcQinQPortEntry 1 }

-- -------------------------------------------------------------
-- groups in the rcQinQ MIB       rcQinQVlanMap
-- -------------------------------------------------------------

rcQinQVlanMap                  OBJECT IDENTIFIER ::= { rcQinQCfg 2 }

rcQinQVlanMapNextIndex             OBJECT-TYPE
        SYNTAX INTEGER (0..65535)
        MAX-ACCESS read-write
        STATUS current
        DESCRIPTION
            "Index of vlan map table."
        ::= { rcQinQVlanMap 1 } 
 
rcQinQVlanMapEnableStatus             OBJECT-TYPE
        SYNTAX EnableVar
        MAX-ACCESS read-write
        STATUS current
        DESCRIPTION
            "Vlan mapping enable status."
        ::= { rcQinQVlanMap 3 }

rcQinQVlanMapPortTable         OBJECT-TYPE
        SYNTAX      SEQUENCE OF RcQinQVlanMapPortEntry
        MAX-ACCESS  not-accessible
        STATUS      current
        DESCRIPTION
            "Vlan mapping table of port."
        ::= { rcQinQVlanMap 2 }

rcQinQVlanMapPortEntry         OBJECT-TYPE
        SYNTAX      RcQinQVlanMapPortEntry
        MAX-ACCESS  not-accessible
        STATUS      current
        DESCRIPTION
            "An entry in the rcQinQVlanMapPortTable. "
	    INDEX        { rcPortIndex, rcQinQVlanMapIndex }    
        ::={ rcQinQVlanMapPortTable 1 }
    
        RcQinQVlanMapPortEntry ::= SEQUENCE 
        {
    	    rcQinQVlanMapIndex	      INTEGER,
    	    rcQinQVlanMapCeVlanList   Vlanset,
            rcQinQVlanMapPeVlanList   Vlanset,
            rcQinQVlanMapInnerVlanId  INTEGER,
            rcQinQVlanMapOuterVlanId  INTEGER,
            rcQinQVlanMapMode         INTEGER,
            rcQinQVlanMapHwStatus     EnableVar,
            rcQinQVlanMapRowStatus    RowStatus,
            rcQinQVlanMapID	          INTEGER,
            rcQinqVlanMapInnerMode    INTEGER,
            rcQinQVlanMapOuterMode    INTEGER,  
            rcQinQVlanMapOuterCosStatus     EnableVar,
            rcQinQVlanMapOuterCos     INTEGER
        }
  
rcQinQVlanMapIndex    OBJECT-TYPE
        SYNTAX        INTEGER (1..65535)
        MAX-ACCESS    not-accessible
        STATUS        current
        DESCRIPTION
            "Index of vlan mapping table."
        ::= { rcQinQVlanMapPortEntry 1 }      
 
rcQinQVlanMapCeVlanList          OBJECT-TYPE
        SYNTAX        Vlanset
        MAX-ACCESS    read-create
        STATUS        current
        DESCRIPTION
            "Customer vlan list for translation."
        ::= { rcQinQVlanMapPortEntry 2 }

rcQinQVlanMapPeVlanList          OBJECT-TYPE
        SYNTAX        Vlanset
        MAX-ACCESS    read-create
        STATUS        current
        DESCRIPTION
            "Provider vlan list for translation."
        ::= { rcQinQVlanMapPortEntry 3 }

rcQinQVlanMapInnerVlanId          OBJECT-TYPE
        SYNTAX        INTEGER (1..4094)
        MAX-ACCESS    read-create
        STATUS        current
        DESCRIPTION
            "The vlan ID for customer vlan list to translate."
        ::= { rcQinQVlanMapPortEntry 4 }

rcQinQVlanMapOuterVlanId          OBJECT-TYPE
        SYNTAX        INTEGER (1..4094)
        MAX-ACCESS    read-create
        STATUS        current
        DESCRIPTION
            "The vlan ID for provider vlan list to translate."
        ::= { rcQinQVlanMapPortEntry 5 }

rcQinQVlanMapMode     OBJECT-TYPE
        SYNTAX        INTEGER {
                      other(1),
                      add(2),
                      ingress-translate(3),
                      egress-translate(4)
                      }
        MAX-ACCESS    read-create
        STATUS        current
        DESCRIPTION
            "The mode of vlan mapping type."
        ::= { rcQinQVlanMapPortEntry 6 }
 
rcQinQVlanMapHwStatus     OBJECT-TYPE
        SYNTAX        EnableVar
        MAX-ACCESS    read-create
        STATUS        current
        DESCRIPTION
            "The vlan mapping whether set in hardware or not."
        ::= { rcQinQVlanMapPortEntry 7 }

rcQinQVlanMapRowStatus  OBJECT-TYPE
        SYNTAX      RowStatus
        MAX-ACCESS  read-create
        STATUS      current
        DESCRIPTION
            "Operation status of this table entry."
        ::= { rcQinQVlanMapPortEntry 8 }

rcQinQVlanMapID  OBJECT-TYPE
        SYNTAX      INTEGER (0..65535)
        MAX-ACCESS  read-only
        STATUS      current
        DESCRIPTION
            "The vlan mapping rule ID."
        ::= { rcQinQVlanMapPortEntry 9 }

rcQinqVlanMapInnerMode  OBJECT-TYPE
        SYNTAX      INTEGER {
                    other(1),
                    translate(2),
                    remove(3),
                    tagged(4),
                    unchanged(5)
                    }
        MAX-ACCESS  read-create
        STATUS      current
        DESCRIPTION
            "The vlan mapping operation of inner tag."
        ::= { rcQinQVlanMapPortEntry 10 }

rcQinQVlanMapOuterMode  OBJECT-TYPE
        SYNTAX      INTEGER {
                    other(1),
                    translate(2),
                    remove(3),
                    tagged(4),
                    unchanged(5)
                    }
        MAX-ACCESS  read-create
        STATUS      current
        DESCRIPTION
            "The vlan mapping operation of outer tag."
        ::= { rcQinQVlanMapPortEntry 11 }

rcQinQVlanMapOuterCosStatus     OBJECT-TYPE
        SYNTAX        EnableVar
        MAX-ACCESS    read-create
        STATUS        current
        DESCRIPTION
            "The vlan mapping whether set outer tag cos value or not."
        ::= { rcQinQVlanMapPortEntry 12 }
        
rcQinQVlanMapOuterCos           OBJECT-TYPE
        SYNTAX        INTEGER (0..7)
        MAX-ACCESS    read-create
        STATUS        current
        DESCRIPTION
            "The outer cos is provided outer tag cos value to translated."
        ::= { rcQinQVlanMapPortEntry 13 }


rcQinQVlanBothPortTable         OBJECT-TYPE
        SYNTAX      SEQUENCE OF RcQinQVlanBothPortEntry
        MAX-ACCESS  not-accessible
        STATUS      current
        DESCRIPTION
            "Vlan mapping N:1 table of port."
        ::= { rcQinQVlanMap 4 }
        
rcQinQVlanBothPortEntry         OBJECT-TYPE
        SYNTAX      RcQinQVlanBothPortEntry
        MAX-ACCESS  not-accessible
        STATUS      current
        DESCRIPTION
            "An entry in the rcQinQVlanBothPortTable. "
	    INDEX        { rcPortIndex, rcQinQVlanBothIndex }    
        ::={ rcQinQVlanBothPortTable 1 }
    
        RcQinQVlanBothPortEntry ::= SEQUENCE 
        {
    	    rcQinQVlanBothIndex	           INTEGER,
    	    rcQinQVlanBothCeVlanList       Vlanset,
    	    rcQinQVlanBothInnerVlanId      INTEGER,
    	    rcQinQVlanBothOuterVlanId      INTEGER,
    	    rcQinQVlanBothMode             INTEGER,
    	    rcVlanBothCeTagEnableStatus    EnableVar,
    	    rcVlanBothPeCtagEnableStatus   EnableVar,
    	    rcQinQVlanBothRowStatus        RowStatus          
        }        
        
rcQinQVlanBothIndex    OBJECT-TYPE
        SYNTAX        INTEGER (1..65535)
        MAX-ACCESS    not-accessible
        STATUS        current
        DESCRIPTION
            "Index of vlan mapping Both table."
        ::= { rcQinQVlanBothPortEntry 1 }      
 
rcQinQVlanBothCeVlanList          OBJECT-TYPE
        SYNTAX        Vlanset    	    
        MAX-ACCESS    read-create
        STATUS        current
        DESCRIPTION
            "Customer vlan list for translation."
        ::= { rcQinQVlanBothPortEntry 2 }

rcQinQVlanBothInnerVlanId          OBJECT-TYPE
        SYNTAX        INTEGER (1..4094)
        MAX-ACCESS    read-create
        STATUS        current
        DESCRIPTION
            "The vlan ID for provider vlan list to translate."
        ::= { rcQinQVlanBothPortEntry 3 }

rcQinQVlanBothOuterVlanId          OBJECT-TYPE
        SYNTAX        INTEGER (1..4094)
        MAX-ACCESS    read-create
        STATUS        current
        DESCRIPTION
            "The vlan ID for provider vlan list to translate."
        ::= { rcQinQVlanBothPortEntry 4 }

rcQinQVlanBothMode     OBJECT-TYPE
        SYNTAX        INTEGER {
                      both-one-translate(5),
                      both-n-translate(6)
                      }
        MAX-ACCESS    read-create
        STATUS        current
        DESCRIPTION
            "The mode of vlan both mapping type."
        ::= { rcQinQVlanBothPortEntry 5 } 

rcVlanBothCeTagEnableStatus             OBJECT-TYPE
        SYNTAX EnableVar
        MAX-ACCESS read-create
        STATUS current
        DESCRIPTION
            "Vlan both mapping client tag enable status."
        ::= { rcQinQVlanBothPortEntry 6 }  
        
rcVlanBothPeCtagEnableStatus             OBJECT-TYPE
        SYNTAX EnableVar
        MAX-ACCESS read-create
        STATUS current
        DESCRIPTION
            "Vlan both mapping provide ctag enable status."
        ::= { rcQinQVlanBothPortEntry 7 }    
 
rcQinQVlanBothRowStatus     OBJECT-TYPE
        SYNTAX        RowStatus
        MAX-ACCESS    read-create
        STATUS        current
        DESCRIPTION
            "The vlan mapping both whether set in hardware or not."
        ::= { rcQinQVlanBothPortEntry 8 }
               
rcVlanPktRepEnableStatus  OBJECT-TYPE
        SYNTAX EnableVar
        MAX-ACCESS read-write
        STATUS current
        DESCRIPTION
            "globally set the Packet Replication;enable(1)means 
            Packet Replication is enabled on this device; disable(2) 
            means Packet Replication is disable on this device."
        ::= { rcQinQVlanMap 5 }

END
