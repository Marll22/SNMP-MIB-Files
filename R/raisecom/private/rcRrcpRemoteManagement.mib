-- *****************************************************************
-- RAISECOM-RRCP-VLAN-MIB.mib:   Raisecom RRCP remote vlan file 
--
-- Copyright (c) 1994-2004 by Raisecom, Inc.
-- All rights reserved.
--
-- *****************************************************************
RAISECOM-RRCP-VLAN-MIB  DEFINITIONS ::= BEGIN

IMPORTS    
        Unsigned32               		  FROM SNMPv2-SMI    -- [RFC2578] 
        iscomSwitch                       FROM RAISECOM-BASE-MIB
        MacAddress                  	  FROM SNMPv2-TC
        RowStatus, TruthValue             FROM SNMPv2-TC
        Vlanset, PortList, EnableVar      FROM SWITCH-TC
        rcPortIndex          		      FROM SWITCH-SYSTEM-MIB;
 
rcRrcp             OBJECT IDENTIFIER ::= { iscomSwitch 52 }

rcRrcpRemoteManagement          MODULE-IDENTITY
    LAST-UPDATED   "200907060000Z"
    ORGANIZATION   "Raisecom, Inc."
    CONTACT-INFO  
                "       Raise Systems
                        
                Postal: Beijing,
                        China

                   Tel: 86-010-82884499

                E-mail: wangjing_rj@raisecom.com"
    DESCRIPTION
        "This MIB module defines objects to RRCP remote VLAN "
        REVISION   "200907060000Z"
        DESCRIPTION
            "The initial revision of this MIB."
        ::={ rcRrcp 2 } 

-- -------------------------------------------------------------
-- groups in the rcRrcpRemoteManagement MIB     rcRemoteVlanConifg
-- -------------------------------------------------------------
rcRemoteVlanConifg    OBJECT IDENTIFIER ::= { rcRrcpRemoteManagement 1 }      
rcRemotePortConfig    OBJECT IDENTIFIER ::= { rcRrcpRemoteManagement 2 } 

-- -------------------------------------------------------------
-- rcRemoteConfigTable
-- -------------------------------------------------------------
rcRemoteConfigTable              OBJECT-TYPE
        SYNTAX      SEQUENCE OF RcRemoteConfigEntry
        MAX-ACCESS  not-accessible
        STATUS      current
        DESCRIPTION
            "Rrcp remote config table."
        ::= { rcRemoteVlanConifg 1 }

rcRemoteConfigEntry               OBJECT-TYPE
        SYNTAX      RcRemoteConfigEntry
        MAX-ACCESS  not-accessible
        STATUS      current
        DESCRIPTION
            "An entry in the rcRemoteConfigTable. It contains
             some configure of remote device."
	    INDEX        { rcRemoteHostMacAddr }    
        ::={ rcRemoteConfigTable 1 }
    
        RcRemoteConfigEntry ::= SEQUENCE
        {
    	    rcRemoteHostMacAddr	              MacAddress,
    	    rcRemoteHostName                  OCTET STRING,
    	    rcRemoteBroadcastStormCtrl        EnableVar,
    	    rcRemoteLoopbackDetection         EnableVar,
    	    rcRemoteLoopbackDetectionStatus   PortList,
    	    rcRemoteDeviceManageVlan          INTEGER,
    	    rcRemoteDeviceReboot              TruthValue,
    	    rcRemoteDeviceCfgWrite            TruthValue,
    	    rcRemoteDeviceCfgWriteResult      INTEGER,
    	    rcRemoteDeviceResetFactory        TruthValue,
    	    rcRemoteDeviceResetFactoryResult  INTEGER    	        	        	    	
        }

rcRemoteHostMacAddr             OBJECT-TYPE
        SYNTAX  MacAddress
        MAX-ACCESS not-accessible
        STATUS current
        DESCRIPTION
            "The MAC address of remote device."
        ::= { rcRemoteConfigEntry 1 }

rcRemoteHostName             OBJECT-TYPE
        SYNTAX  OCTET STRING(SIZE(1..32))
        MAX-ACCESS read-write
        STATUS current
        DESCRIPTION
            "The host name of remote device."
        ::= { rcRemoteConfigEntry 2 }

rcRemoteBroadcastStormCtrl             OBJECT-TYPE
        SYNTAX  EnableVar
        MAX-ACCESS read-write
        STATUS current
        DESCRIPTION
            "The broadcast storm control status of remote device."
        ::= { rcRemoteConfigEntry 3 }

rcRemoteLoopbackDetection             OBJECT-TYPE
        SYNTAX  EnableVar
        MAX-ACCESS read-write
        STATUS current
        DESCRIPTION
            "The loop back detection status of remote device."
        ::= { rcRemoteConfigEntry 4 }

rcRemoteLoopbackDetectionStatus       OBJECT-TYPE
        SYNTAX  PortList
        MAX-ACCESS read-only
        STATUS current
        DESCRIPTION
            "The loop back detection result information of remote device."
        ::= { rcRemoteConfigEntry 5 }
        
rcRemoteDeviceManageVlan       OBJECT-TYPE
        SYNTAX   INTEGER
        MAX-ACCESS read-write
        STATUS current
        DESCRIPTION
            "The management vlan of remote device."
        ::= { rcRemoteConfigEntry 6 }

rcRemoteDeviceCfgWrite       OBJECT-TYPE
        SYNTAX   TruthValue
        MAX-ACCESS read-write
        STATUS current
        DESCRIPTION
            "Write remote device config to hardware."
        ::= { rcRemoteConfigEntry 7 }
        
rcRemoteDeviceCfgWriteResult       OBJECT-TYPE
        SYNTAX   INTEGER
        {
            other(1),
            saving(2),
            successed(3),
            failed(4)
        } 
        MAX-ACCESS read-only
        STATUS current
        DESCRIPTION
            "Result of write remote device config to hardware."
        ::= { rcRemoteConfigEntry 8 }

rcRemoteDeviceResetFactory       OBJECT-TYPE
        SYNTAX   TruthValue
        MAX-ACCESS read-write
        STATUS current
        DESCRIPTION
            "Recover default config and reboot remote device."
        ::= { rcRemoteConfigEntry 9 }
        
rcRemoteDeviceResetFactoryResult       OBJECT-TYPE
        SYNTAX  INTEGER
        {
            other(1),
            factory-reseting(2),
            successed(3),
            failed(4)
        } 
        MAX-ACCESS read-only
        STATUS current
        DESCRIPTION
            "Result of recover default config and reboot remote device."
        ::= { rcRemoteConfigEntry 10 }
        
rcRemoteDeviceReboot       OBJECT-TYPE
        SYNTAX   TruthValue
        MAX-ACCESS read-write
        STATUS current
        DESCRIPTION
            "Reboot remote device."
        ::= { rcRemoteConfigEntry 11 }
        
-- -------------------------------------------------------------
-- rcRemoteVlanCfgTable
-- -------------------------------------------------------------
rcRemoteVlanCfgTable               OBJECT-TYPE
        SYNTAX      SEQUENCE OF RcRemoteVlanCfgEntry
        MAX-ACCESS  not-accessible
        STATUS      current
        DESCRIPTION
            "Remote device vlan config table."
        ::= { rcRemoteVlanConifg 2 }

rcRemoteVlanCfgEntry               OBJECT-TYPE
        SYNTAX      RcRemoteVlanCfgEntry
        MAX-ACCESS  not-accessible
        STATUS      current
        DESCRIPTION
            "An entry in the rcRemoteVlanCfgTable. It contains
             some vlan configure of remote device."
	    INDEX        { rcRemoteHostMacAddr }    
        ::={ rcRemoteVlanCfgTable 1 }
    
        RcRemoteVlanCfgEntry ::= SEQUENCE
        {
            rcRemoteSwitchMode                 INTEGER,
            rcRemotePortBasedVlanUpLinkPort    INTEGER  	        	    	
        }

rcRemoteSwitchMode                    OBJECT-TYPE
        SYNTAX  INTEGER
        {
            transparent(1),
            dot1q-vlan(2),
            port-based-vlan(3)
        }        
        MAX-ACCESS read-write
        STATUS current
        DESCRIPTION
            "Switch mode of remote device."
        ::= { rcRemoteVlanCfgEntry 1 }
 
rcRemotePortBasedVlanUpLinkPort       OBJECT-TYPE
        SYNTAX  INTEGER(1..65535)
        MAX-ACCESS read-write
        STATUS current
        DESCRIPTION
            "The up link port in port-based-mode of remote device."
        ::= { rcRemoteVlanCfgEntry 2 }
 
 
-- -------------------------------------------------------------
-- rcRemoteCurrentVlanTable
-- -------------------------------------------------------------
rcRemoteCurrentVlanTable               OBJECT-TYPE
        SYNTAX      SEQUENCE OF RcRemoteCurrentVlanEntry
        MAX-ACCESS  not-accessible
        STATUS      current
        DESCRIPTION
            "Remote device current vlan config table."
        ::= { rcRemoteVlanConifg 3 }

rcRemoteCurrentVlanEntry               OBJECT-TYPE
        SYNTAX      RcRemoteCurrentVlanEntry
        MAX-ACCESS  not-accessible
        STATUS      current
        DESCRIPTION
            "An entry in the rcRemoteCurrentVlanTable. It contains
             current vlan configure of remote device."
	    INDEX        { rcRemoteHostMacAddr, rcRemoteCurrentVlanIndex }    
        ::={ rcRemoteCurrentVlanTable 1 }
    
        RcRemoteCurrentVlanEntry ::= SEQUENCE
        {
            rcRemoteCurrentVlanIndex           INTEGER,
            rcRemoteCurrentVlanEgressPorts     PortList,
            rcRemoteCurrentVlanRowStatus       RowStatus  	        	    	
        }

rcRemoteCurrentVlanIndex                    OBJECT-TYPE
        SYNTAX  INTEGER(1..4094)      
        MAX-ACCESS not-accessible
        STATUS current
        DESCRIPTION
            "The VLAN id of remote device created."
        ::= { rcRemoteCurrentVlanEntry 1 }

rcRemoteCurrentVlanEgressPorts                    OBJECT-TYPE
        SYNTAX  PortList      
        MAX-ACCESS read-only
        STATUS current
        DESCRIPTION
            "The set of ports that are transmitting traffic for 
            this VLAN as either tagged or untagged frames."
        ::= { rcRemoteCurrentVlanEntry 2 }

rcRemoteCurrentVlanRowStatus                      OBJECT-TYPE
        SYNTAX  RowStatus                  
        MAX-ACCESS read-create
        STATUS current
        DESCRIPTION
            "This object indicates the status of this entry."
        ::= { rcRemoteCurrentVlanEntry 3 }


-- -------------------------------------------------------------
-- rcRemoteVlanPortTable
-- -------------------------------------------------------------
rcRemoteVlanPortTable               OBJECT-TYPE
        SYNTAX      SEQUENCE OF RcRemoteVlanPortEntry
        MAX-ACCESS  not-accessible
        STATUS      current
        DESCRIPTION
            "Remote device vlan port config table."
        ::= { rcRemoteVlanConifg 4 }

rcRemoteVlanPortEntry               OBJECT-TYPE
        SYNTAX      RcRemoteVlanPortEntry
        MAX-ACCESS  not-accessible
        STATUS      current
        DESCRIPTION
            "An entry in the rcRemoteVlanPortTable. It contains
             port vlan configure of remote device."
	    INDEX        { rcRemoteHostMacAddr, rcRemotePortIndex }    
        ::={ rcRemoteVlanPortTable 1 }
    
        RcRemoteVlanPortEntry ::= SEQUENCE
        {
            rcRemotePortIndex                  INTEGER,
            rcRemotePortMode                   INTEGER,
            rcRemotePortNativeVid              INTEGER,
            rcRemotePortAccessEgressAllowVlan  Vlanset,  
            rcRemotePortTrunkAllowVlan  Vlanset	        	    	
        }

rcRemotePortIndex                    OBJECT-TYPE
        SYNTAX  INTEGER(1..65535)      
        MAX-ACCESS not-accessible
        STATUS current
        DESCRIPTION
            "The port index of remote device."
        ::= { rcRemoteVlanPortEntry 1 }

rcRemotePortMode                    OBJECT-TYPE
        SYNTAX  INTEGER
        {
            access(1),
            trunk(2)
        }      
        MAX-ACCESS read-write
        STATUS current
        DESCRIPTION
            "The VLAN port mode of remote device."
        ::= { rcRemoteVlanPortEntry 2 }

rcRemotePortNativeVid                    OBJECT-TYPE
        SYNTAX  INTEGER(1..4094)    
        MAX-ACCESS read-write
        STATUS current
        DESCRIPTION
            "Native vlan ID of interface for remote device."
        ::= { rcRemoteVlanPortEntry 3 }

rcRemotePortAccessEgressAllowVlan        OBJECT-TYPE
        SYNTAX  Vlanset    
        MAX-ACCESS read-write
        STATUS current
        DESCRIPTION
            "Egress VLAN list when port is in access mode of remote device."
        ::= { rcRemoteVlanPortEntry 4 }

rcRemotePortTrunkAllowVlan        OBJECT-TYPE
        SYNTAX  Vlanset    
        MAX-ACCESS read-write
        STATUS current
        DESCRIPTION
            "VLAN list when port is in trunk mode of remote device."
        ::= { rcRemoteVlanPortEntry 5 }

-- -------------------------------------------------------------
-- rcRemoteQosCfgTable
-- -------------------------------------------------------------
rcRemoteQosCfgTable               OBJECT-TYPE
        SYNTAX      SEQUENCE OF RcRemoteQosCfgEntry
        MAX-ACCESS  not-accessible
        STATUS      current
        DESCRIPTION
            "Remote device qos config table."
        ::= { rcRemoteVlanConifg 5 }

rcRemoteQosCfgEntry               OBJECT-TYPE
        SYNTAX      RcRemoteQosCfgEntry
        MAX-ACCESS  not-accessible
        STATUS      current
        DESCRIPTION
            "An entry in the rcRemoteQosCfgTable. It contains
             qos configure of remote device."
	    INDEX        { rcRemoteHostMacAddr }    
        ::={ rcRemoteQosCfgTable 1 }
    
        RcRemoteQosCfgEntry ::= SEQUENCE
        {
            rcRemoteMlsQosTrustMode            INTEGER,
            rcRemoteMlsQosScheduleMode         INTEGER,
            rcRemoteMlsQosQueueWeight          INTEGER,
            rcRemoteMlsQosPortPriorityList     PortList  	        	    	
        }

rcRemoteMlsQosTrustMode                    OBJECT-TYPE
        SYNTAX  INTEGER
        {
            port-priority(1),
            cos(2)
        }      
        MAX-ACCESS read-write
        STATUS current
        DESCRIPTION
            "Qos trust mode of remote device."
        ::= { rcRemoteQosCfgEntry 1 }

rcRemoteMlsQosScheduleMode                    OBJECT-TYPE
        SYNTAX  INTEGER
        {
            sp(1),
            wrr(2)
        }      
        MAX-ACCESS read-write
        STATUS current
        DESCRIPTION
            "Qos queue schedule mode of remote device."
        ::= { rcRemoteQosCfgEntry 2 }
        
rcRemoteMlsQosQueueWeight                    OBJECT-TYPE
        SYNTAX  INTEGER
        {
            fourth(1),
            eighth(2),
            sixteen(3),
            other(4)
        }      
        MAX-ACCESS read-write
        STATUS current
        DESCRIPTION
            "Qos wrr queue weight of remote device."
        ::= { rcRemoteQosCfgEntry 3 }
 
rcRemoteMlsQosPortPriorityList                    OBJECT-TYPE
        SYNTAX  PortList
        MAX-ACCESS read-write
        STATUS current
        DESCRIPTION
            "The port priority list of remote device."
        ::= { rcRemoteQosCfgEntry 4 }


-------------------------------------------------------
-- Config Trap Notification                                   
-------------------------------------------------------
rcRemoteConfigNotifications   OBJECT IDENTIFIER ::= { rcRemoteVlanConifg 6 }      

rcRemoteConfigWriteResultNotification
    NOTIFICATION-TYPE   OBJECTS
    {
        rcRemoteHostMacAddr,
        rcRemoteDeviceCfgWriteResult      
    }
    STATUS      current
    DESCRIPTION
       "This Notification indicate result of write remote device config, the
        notifications will be emitted by the same object instance."
    REFERENCE
       ""
    ::= { rcRemoteConfigNotifications 1 }
         
rcRemoteConfigResetFactoryResultNotification
    NOTIFICATION-TYPE    OBJECTS
    {     
        rcRemoteHostMacAddr,
        rcRemoteDeviceResetFactoryResult
    }
    STATUS      current
    DESCRIPTION
       "This Notification indicate result of factory-reset remote device config,
        the notifications will be emitted by the same object instance."
    REFERENCE
       ""
    ::= { rcRemoteConfigNotifications 2 }

------------------------------------------------------        
-- Remote port config attribution Table   
------------------------------------------------------
rcRemotePortConfigAttriTable OBJECT-TYPE
    SYNTAX      SEQUENCE OF RcRemotePortConfigAttriEntry
    MAX-ACCESS  not-accessible
    STATUS      current
    DESCRIPTION
        "Remote port config attribution Table"
    ::= { rcRemotePortConfig 1 }

rcRemotePortConfigAttriEntry   OBJECT-TYPE
    SYNTAX      RcRemotePortConfigAttriEntry
    MAX-ACCESS  not-accessible 
    STATUS      current
    DESCRIPTION
        "An entry in the rcRemotePortConfigAttriTable. It contains
        configuration in each port."
	INDEX        { rcRemoteHostMacAddr , rcRemotePortIndex  }    
    ::={ rcRemotePortConfigAttriTable 1 }
    
    RcRemotePortConfigAttriEntry ::= SEQUENCE {
 	 rcRemotePortAdminStatus				EnableVar,        
	 rcRemotePortOperStatus                 EnableVar, 
	 rcRemotePortDuplexSpeedSet             INTEGER,   
	 rcRemotePortDuplexSpeedGet             INTEGER,  
	 rcRemoteManPortFlowControlEnable       EnableVar,
	 rcRemotePortRxRateLimit                INTEGER,
	 rcRemotePortTxRateLimit                INTEGER
	 }
     
rcRemotePortAdminStatus        OBJECT-TYPE
	SYNTAX EnableVar
    MAX-ACCESS  read-write
    STATUS      current
    DESCRIPTION
            "The administration status of port."
    ::= { rcRemotePortConfigAttriEntry 1 }  
        
rcRemotePortOperStatus        OBJECT-TYPE
	SYNTAX INTEGER   {
               up(1),
               down(2)
          }
    MAX-ACCESS  read-only
    STATUS      current
    DESCRIPTION
            "The operation status of port."
    ::= { rcRemotePortConfigAttriEntry 2 }   
     
rcRemotePortDuplexSpeedSet        OBJECT-TYPE
		SYNTAX INTEGER   {
               autonegotiate(1),
               half-10(2),   
               full-10(3),
               half-100(4),
               full-100(5)
          }
    MAX-ACCESS  read-write
    STATUS      current
    DESCRIPTION
            "The desired speed and duplex of the interface in remote devices.."
    ::= { rcRemotePortConfigAttriEntry 3 }       
    
rcRemotePortDuplexSpeedGet        OBJECT-TYPE
		SYNTAX INTEGER   {
               unknown(1),
               half-10(2),   
               full-10(3),
               half-100(4),
               full-100(5),
               illegal(99)
          }
    MAX-ACCESS  read-only
    STATUS      current
    DESCRIPTION
            "The actual speed and duplex for this interface. 
            If the interface is not configured for an acceptable value, 
            a value of illegal(99) is returned. A value of unknown(1) 
            is returned when the interface is down."
    ::= { rcRemotePortConfigAttriEntry 4 }    
    
rcRemoteManPortFlowControlEnable        OBJECT-TYPE
	SYNTAX EnableVar
    MAX-ACCESS  read-write
    STATUS      current
    DESCRIPTION
            "Describes flow control of the port of  remote device
            A value of enabled(1)- indicates that the port can process flow-control.
            A value of disabled(2)- indicates that the port can  not process flow-control."
    ::= { rcRemotePortConfigAttriEntry 5 }

rcRemotePortRxRateLimit        OBJECT-TYPE
	SYNTAX INTEGER ( 0 | 128..8000)
    MAX-ACCESS  read-write
    STATUS      current
    DESCRIPTION
            "Describes rate-limit value of the port of remote device at rx direction
             0 value is no rate-limit."
    ::= { rcRemotePortConfigAttriEntry 6 }    
    
rcRemotePortTxRateLimit        OBJECT-TYPE
	SYNTAX INTEGER (0 | 128..8000) 
    MAX-ACCESS  read-write
    STATUS      current
    DESCRIPTION
            "Describes rate-limit value of the port of remote device at tx direction
             0 value is no rate-limit."
    ::= { rcRemotePortConfigAttriEntry 7 }            
                                               
                                               
-----------------------------------------------
-- remote port vct Table   
-----------------------------------------------
rcRemotePortVctTable OBJECT-TYPE
    SYNTAX      SEQUENCE OF RcRemotePortVctEntry
    MAX-ACCESS  not-accessible
    STATUS      current
    DESCRIPTION
        "A table of objects that display vct status
            of ports."
    ::= { rcRemotePortConfig 2 }

rcRemotePortVctEntry   OBJECT-TYPE
    SYNTAX      RcRemotePortVctEntry
    MAX-ACCESS  not-accessible
    STATUS      current
    DESCRIPTION
        "A set of objects that display vct status."
	INDEX        { rcRemoteHostMacAddr, rcRemotePortIndex}    
    ::={ rcRemotePortVctTable 1 }
    
    RcRemotePortVctEntry ::= SEQUENCE { 
    rcRemotePortVCTStart                       INTEGER,
   	rcRemotePortVctCableTxStatus			   INTEGER,  
   	rcRemotePortVctCableRxStatus			   INTEGER,
    rcRemotePortVctCableTxLength			   Unsigned32, 
	rcRemotePortVctCableRxLength			   Unsigned32   
	}

rcRemotePortVCTStart        OBJECT-TYPE
	SYNTAX INTEGER   {
	         none (0),
             started (1),
             stoped (2)
             }
    MAX-ACCESS  read-write
    STATUS      current
    DESCRIPTION
            "Describes vct is started or not.
             A value of none (0)- indicates that vct has not been started.
             A value of started (1)- indicates that vct has been started.
             A value of stoped (2)- indicates t that vct has been stoped."
    ::= { rcRemotePortVctEntry 1 }    

rcRemotePortVctCableTxStatus        OBJECT-TYPE
	SYNTAX INTEGER   {
             normal(1), 
 	         open(2), 
 	         shorted(3), 
 	         error(4), 
             testing(5)
             }
    MAX-ACCESS  read-only
    STATUS      current
    DESCRIPTION
            "This object identifies the tx direction status of  remote device."
    ::= { rcRemotePortVctEntry 2 }  
    
rcRemotePortVctCableRxStatus        OBJECT-TYPE
	SYNTAX INTEGER   {
             normal(1), 
 	         open(2), 
 	         shorted(3), 
 	         error(4), 
             testing(5)
             }
    MAX-ACCESS  read-only
    STATUS      current
    DESCRIPTION
            "This object identifies the rx direction status of  remote device."
    ::= { rcRemotePortVctEntry 3 }     
 
rcRemotePortVctCableTxLength        OBJECT-TYPE
	SYNTAX      Unsigned32
    MAX-ACCESS  read-only
    STATUS      current
    DESCRIPTION
            "This object identifies the tx direction length of  remote device."
    ::= { rcRemotePortVctEntry 4 }  
rcRemotePortVctCableRxLength        OBJECT-TYPE
	SYNTAX      Unsigned32
    MAX-ACCESS  read-only
    STATUS      current
    DESCRIPTION
            "This object identifies the rx direction length of  remote device."
    ::= { rcRemotePortVctEntry 5 }    
 
-------------------------------------------------
--remote  port statistics table      
-------------------------------------------------
rcRemotePortStatisticsTable OBJECT-TYPE
    SYNTAX      SEQUENCE OF RcRemotePortStatisticsEntry
    MAX-ACCESS  not-accessible
    STATUS      current
    DESCRIPTION
        "A table of objects that display statistics of ports."
    ::= { rcRemotePortConfig 3 }

rcRemotePortStatisticsEntry   OBJECT-TYPE
    SYNTAX      RcRemotePortStatisticsEntry
    MAX-ACCESS  not-accessible
    STATUS      current
    DESCRIPTION
        "A set of objects that display port statistics."
	INDEX        { rcRemoteHostMacAddr , rcRemotePortIndex}    
    ::={ rcRemotePortStatisticsTable 1 }
    
    RcRemotePortStatisticsEntry ::= SEQUENCE {
   	rcRemotePortRxOctets			   Unsigned32,
	rcRemotePortTxOctets			   Unsigned32,        
	rcRemotePortDropOctets             Unsigned32
	}
	
rcRemotePortRxOctets        OBJECT-TYPE
	SYNTAX      Unsigned32
    MAX-ACCESS  read-only
    STATUS      current
    DESCRIPTION
            "The total number of octets received on the port."
    ::= { rcRemotePortStatisticsEntry 1 } 
    
rcRemotePortTxOctets        OBJECT-TYPE
	SYNTAX      Unsigned32
    MAX-ACCESS  read-only
    STATUS      current
    DESCRIPTION
            "The total number of octets transmitted out of the port."
    ::= { rcRemotePortStatisticsEntry 2 }
    
rcRemotePortDropOctets        OBJECT-TYPE
	SYNTAX      Unsigned32
    MAX-ACCESS  read-only
    STATUS      current
    DESCRIPTION
            "The total number of octets droped out of or in of the port."
    ::= { rcRemotePortStatisticsEntry 3 }

-------------------------------------------------------
-- trap notification                                   
-------------------------------------------------------
rcRemotePortNotifications   OBJECT IDENTIFIER ::= { rcRemotePortConfig 4 }      

rcRemotePortUpNotification
NOTIFICATION-TYPE
    OBJECTS     { rcRemoteManPortOperStatus      
                }
    STATUS      current
    DESCRIPTION
       "This Notification indicate remote device port is in up status , 
       the notifications will be emitted by the same object instance."
    REFERENCE
       ""
    ::= { rcRemotePortNotifications 1 }
         
rcRemotePortDownNotification
NOTIFICATION-TYPE
    OBJECTS     { rcRemoteManPortOperStatus
                }
    STATUS      current
    DESCRIPTION
       "This Notification indicate remote device port is in down status , 
       the notifications will be emitted by the same object instance."
    REFERENCE
       ""
    ::= { rcRemotePortNotifications 2 }
   

END
