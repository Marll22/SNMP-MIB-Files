--MibName=raisecomSyslogService
-- =======================================================================
-- Syslog Service info 
--
-- Version 0.1 Created 2003.12.17 by GONGGUIDONG
-- This version of MIB is created just for the use of Network Management Systems
-- display and config the syslog service.
-- log:
-- change raisecomSyslogService from OBJECT-TYPE to MODULE-IDENTITY  by gongguidong  20040205
-- change raisecomSyslogDirection from read-write to read-only   by gongguidong  20040205 
--
-- Copyright(c) 2003-2005 by RAISECOM TECH, Ltd.
-- =======================================================================

--RAISECOM-SYSLOG-SERVICE-MIB
--2003/2/17
-- This MIB provides a means to gather syslog messages generated
-- by the RaisecomOS

-- Terminology:
-- Various textual messages are generated by the RaisecomOS.  The RaisecomOS
-- can be configured such that these messages are sent to a "syslog"
-- server.   These messages are hereupon referred to as "syslog
-- messages" in this document. Note: Messages generated as a result 
-- of entering CLI debug commands are not made available via the SNMP
-- at this time.
-- 
-- All syslog messages have the following attributes:
--	timestamp (optional), facility name (where the message came
--	from), severity, message name, message text
--
-- The following example is often seen:
--	%SYS-5-CONFIG_I: Configured from console ...
-- where facility=SYS, severity=5, message name=CONFIG_I
-- ===========================================================================
-- RAISECOM syslog service objects

RAISECOM-SYSLOG-SERVICE-MIB    DEFINITIONS ::= BEGIN

	IMPORTS
		MODULE-IDENTITY,
		OBJECT-TYPE,
		IpAddress
			FROM SNMPv2-SMI
		RowStatus
			FROM SNMPv2-TC   
		EnableVar
			FROM SWITCH-TC
		raisecomAgent		
			FROM RAISECOM-BASE-MIB;
	
			
	
--  Syslog Service MIB


	raisecomSyslogService	MODULE-IDENTITY
        LAST-UPDATED 	"200412210000Z"
        ORGANIZATION 	"RAISECOM TECH, Ltd."
        CONTACT-INFO 	"www.raisecom.com"
        DESCRIPTION  	
            "The MIB module defining objects for Syslog Service"
    ::= { raisecomAgent 4 }


-- Textual Conventions

	SyslogSeverity ::= TEXTUAL-CONVENTION
		STATUS	current
		DESCRIPTION
	   	    	"The severity of a syslog message.  The enumeration
				values are equal to the values that syslog uses + 1.
				For example, with syslog, emergency=0."
		SYNTAX	INTEGER {
			emergency(1),
			alert(2),
			critical(3),
			error(4),
			warning(5),
			notice(6),
			info(7),
			debug(8)
		}
		
		
raisecomSyslogMibObjects OBJECT IDENTIFIER ::= { raisecomSyslogService 1 }

-- Subgroups 供以后扩展使用

raisecomLogBasic	OBJECT IDENTIFIER ::= { raisecomSyslogMibObjects 1 }
raisecomLogServer	OBJECT IDENTIFIER ::= { raisecomSyslogMibObjects 2 }
raisecomDebug		OBJECT IDENTIFIER ::= { raisecomSyslogMibObjects 3 }



	--raisecomLogBasic
		raisecomLogEnable OBJECT-TYPE
		SYNTAX EnableVar
			ACCESS read-write
			STATUS current
			DESCRIPTION
					"The administration status of the syslog function is enable or disable."
				::= { raisecomLogBasic 1 }
      	
		 
	 	raisecomLogRateLimit OBJECT-TYPE	 	
		SYNTAX INTEGER (0..10000)
			ACCESS read-write
			STATUS current
			DESCRIPTION
					"The Rate Limit for syslog."
				::= { raisecomLogBasic 2 }
				
		raisecomLogDropMessages OBJECT-TYPE	 	
			SYNTAX INTEGER (0..2147483647) 
			ACCESS read-only
			STATUS current
			DESCRIPTION
					"The number of messages that syslog droped."
				::= { raisecomLogBasic 3 }
		
		raisecomLogConsoleLogedMessages OBJECT-TYPE	 	
			SYNTAX INTEGER (0..2147483647)
			ACCESS read-only
			STATUS current
			DESCRIPTION
					"The number of messages that syslog loged to console."
				::= { raisecomLogBasic 4 }
				
		raisecomLogMonitorMessages OBJECT-TYPE	 	
			SYNTAX INTEGER (0..2147483647)
			ACCESS read-only
			STATUS current
			DESCRIPTION
					"The number of messages that syslog loged to Monitor."
				::= { raisecomLogBasic 5 }
		
		raisecomLogTimeStamp 	OBJECT-TYPE	 	
			SYNTAX INTEGER {
						no-timestamp(1),
						stand-timestamp(2),
						relative-timestamp(3)
						}
			ACCESS read-write
			STATUS current  
			DESCRIPTION
					"
					no-timestamp   no time stamp
					stand-timestamp  : APR-26-2004 17:27:45 
					relative-timestamp 17:27:45 time from start up
					"      
			DEFVAL { stand-timestamp }
					::= { raisecomLogBasic 6 }	
				
				
				
		
	-- The raisecom Syslog Service Server Control group
  	--
  	-- The raisecom syslog service server control contains 
   	-- configing syslog service logto server setting.      
	-- The raisecomSyslogServiceServerControl Table   
	             
	raisecomLogMaxNumberOfLogServer OBJECT-TYPE
              	SYNTAX INTEGER 
              	ACCESS read-only
              	STATUS current
              	DESCRIPTION
                  	"The Max Number of syslog server "
              	::= { raisecomLogServer 1 }

	raisecomLogServerNumber OBJECT-TYPE
              	SYNTAX INTEGER 
              	ACCESS read-only
              	STATUS current
              	DESCRIPTION
                  	"The Number of syslog server that has been configured "
              	::= { raisecomLogServer 2 }


	raisecomLogServerTable OBJECT-TYPE
              	SYNTAX SEQUENCE OF RaisecomlogServerEntry 
              	ACCESS not-accessible
              	STATUS current
              	DESCRIPTION
                  	"A list of raisecomSyslogServiceServer entries."
              	::= { raisecomLogServer 3 }


	raisecomLogServerEntry OBJECT-TYPE
              	SYNTAX RaisecomlogServerEntry 
              	ACCESS not-accessible
              	STATUS current
              	DESCRIPTION
                  	"The syslog service server list group infomation entry."
              	INDEX { raisecomLogServerIpAddress }
              	::= { raisecomLogServerTable 1 }

	RaisecomlogServerEntry ::= SEQUENCE {
              		raisecomLogServerIpAddress	IpAddress,
              		raisecomLogServerPort	INTEGER,
              		raisecomLogFacility	INTEGER,
					raisecomLogServerMaxSeverity INTEGER, 
					raisecomLogServerRowStatus	RowStatus
          	}

              
	raisecomLogServerIpAddress OBJECT-TYPE
              	SYNTAX IpAddress
              	ACCESS not-accessible
              	STATUS current
              	DESCRIPTION
                  	"The value of this object is the IpAddress of the server to which
                  	the syslog messages will be sent."
              	::= { raisecomLogServerEntry 1 }


	raisecomLogServerPort OBJECT-TYPE
              	SYNTAX INTEGER ( 1 .. 65535)
              	ACCESS read-only
              	STATUS current
              	DESCRIPTION
                  	"The value of this object is the port of the server to which
                  	the syslog messages will be sent."
              	::= { raisecomLogServerEntry 2 }


	raisecomLogFacility OBJECT-TYPE
              	SYNTAX INTEGER{
              		local0(1),
              		local1(2),
              		local2(3),
              		local3(4),
              		local4(5),
              		local5(6),
              		local6(7),
              		local7(8)
               	}

              	ACCESS read-create
              	STATUS current
              	DESCRIPTION
                  	"The facility is one of the following keywords: local0 through local7.
                  	The facility specifies the subsystem that produced the message, i.e. 
                  	all mail programs log with the mail facility (LOG_MAIL) if they log 
                  	using syslog.The default value is local0(0)."
              	::= { raisecomLogServerEntry 3 }


	raisecomLogServerMaxSeverity OBJECT-TYPE
	       	SYNTAX	INTEGER {
			emergency(1),
			alert(2),
			critical(3),
			error(4),
			warning(5),
			notice(6),
			info(7),
			debug(8)
		}
			ACCESS read-create
			STATUS current
			DESCRIPTION
	                  	"The max severity of messages which will be sent to syslog host."
	              	::= { raisecomLogServerEntry 4 }

	raisecomLogServerRowStatus 	OBJECT-TYPE
	  	SYNTAX RowStatus 	
		ACCESS read-create
		STATUS current
		DESCRIPTION
			"This object indicates the status of this entry."
		::= { raisecomLogServerEntry 5 }
--raisecomDebug
--	
	raisecomDebugTable OBJECT-TYPE
              	SYNTAX SEQUENCE OF RaisecomDebugEntry 
              	ACCESS not-accessible
              	STATUS current
              	DESCRIPTION
                  	"A list of raisecom Debug  entries."
              	::= { raisecomDebug 1 }


	raisecomDebugEntry OBJECT-TYPE
              	SYNTAX RaisecomDebugEntry 
              	ACCESS not-accessible
              	STATUS current
              	DESCRIPTION
                  	"The debug  infomation entry."
              	INDEX { raisecomDebugIndex }
              	::= { raisecomDebugTable 1 }

	RaisecomDebugEntry ::= SEQUENCE {
              		raisecomDebugIndex		INTEGER,
              		raisecomDebugModuleName  	OCTET STRING,
              		raisecomDebugModuleEnable	EnableVar
          	}

	raisecomDebugIndex OBJECT-TYPE
	  	SYNTAX INTEGER 	
		ACCESS not-accessible
		STATUS current
		DESCRIPTION
			"This object index of system debug entry."
		::= { raisecomDebugEntry 1 }
		
	raisecomDebugModuleName OBJECT-TYPE
	  	SYNTAX OCTET STRING (SIZE (0..32))
		ACCESS read-write
		STATUS current
		DESCRIPTION
			"This name of debugging module ."
		::= { raisecomDebugEntry 2 }

	raisecomDebugModuleEnable OBJECT-TYPE
	  	SYNTAX EnableVar
		ACCESS read-write
		STATUS current
		DESCRIPTION
			"This switch of specific module ."
		::= { raisecomDebugEntry 3 }
						

END
