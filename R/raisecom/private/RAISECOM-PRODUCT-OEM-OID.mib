--MibName=raisecom
-- =======================================================================
-- Version info 
--
-- Version 0.1 Created 2003.5.24 by GONGGUIDONG
-- This version of MIB is created just for management of base and user. 
-- 
-- Copyright(c) 2000-2002 by Raisecom  Ltd. 

RAISECOM-BASE-OEM-MIB    DEFINITIONS ::= BEGIN

IMPORTS
   oemSeries		FROM RAISECOM-BASE-MIB;

-- =======================================================================
--
--  OEM
-- =======================================================================	
	iscom3408        OBJECT IDENTIFIER ::= { oemSeries 1 } 
	
END
