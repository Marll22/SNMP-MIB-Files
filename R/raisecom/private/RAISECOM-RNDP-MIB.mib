--MibName=raisecomTopoDiscovery
-- *****************************************************************
-- RAISECOM-TOPODISCOVERY-MIB.MIB:  Raisecom Topology Discovery MIB file
--
-- Sep. 2004, xieyong
--
-- Copyright (c) 1994-2004, 2004 by Raisecom, Inc.
-- All rights reserved.
--
-- *****************************************************************
RAISECOM-RNDP-MIB  DEFINITIONS ::= BEGIN

IMPORTS
       raisecomCluster
                FROM RAISECOM-BASE-MIB  
       EnableVar FROM SWITCH-TC
       MacAddress
				FROM SNMPv2-TC;

raisecomTopoDiscovery MODULE-IDENTITY
        LAST-UPDATED    "200412210000Z"
        ORGANIZATION    "Raisecom, Inc."
        CONTACT-INFO
                        "Raisecom Systems

                        Postal: Beijing, China

                        Tel: 86-010-82884499

                        E-mail: xieyong@raisecom.com"
        DESCRIPTION
                        "description of topology discovery."
                ::= {raisecomCluster 2}


    raisecomRndpProtocolEnable OBJECT-TYPE
        SYNTAX  EnableVar
        ACCESS read-write
        STATUS mandatory
        DESCRIPTION
                "Enable(1) or disable(2) rndp on the switch." 
        DEFVAL {disable }
        ::= { raisecomTopoDiscovery 1 }

------------  raisecomRndpDiscoveryTable ----------------
    raisecomRndpDiscoveryTable OBJECT-TYPE
        SYNTAX SEQUENCE OF RaisecomRndpDiscoveryEntry
        MAX-ACCESS not-accessible
        STATUS current
        DESCRIPTION
            "rndp interface discovery table."
        ::= { raisecomTopoDiscovery 2 }

    raisecomRndpDiscoveryEntry OBJECT-TYPE
        SYNTAX RaisecomRndpDiscoveryEntry
        MAX-ACCESS not-accessible
        STATUS current
        DESCRIPTION
            "rndp interface discovery table entry."
        INDEX { raisecomRndpDiscoveryInterfaceId, raisecomRndpDiscoveryDeviceId }
        ::= { raisecomRndpDiscoveryTable 1 }

    RaisecomRndpDiscoveryEntry ::= SEQUENCE {
        raisecomRndpDiscoveryInterfaceId        INTEGER,
        raisecomRndpDiscoveryDeviceId           MacAddress,
        raisecomRndpDiscoveryPortId             INTEGER,
        raisecomRndpDiscoveryHostName           OCTET STRING,
        raisecomRndpDiscoveryPlatformOid        OBJECT IDENTIFIER,
        raisecomRndpDiscoveryVersion            OCTET STRING,
        raisecomRndpDiscoveryCapabilities       INTEGER
     }

    raisecomRndpDiscoveryInterfaceId OBJECT-TYPE
        SYNTAX INTEGER
        MAX-ACCESS read-only
        STATUS current
        DESCRIPTION
            "An index based 1 that uniquely identifies a system interface."
        ::= { raisecomRndpDiscoveryEntry 1 }

    raisecomRndpDiscoveryDeviceId OBJECT-TYPE
        SYNTAX  MacAddress
        MAX-ACCESS read-only
        STATUS current
        DESCRIPTION
            "System mac address, uniquely identifies a remote device."
        ::= { raisecomRndpDiscoveryEntry 2 }

    raisecomRndpDiscoveryPortId OBJECT-TYPE
        SYNTAX  INTEGER
        MAX-ACCESS read-only
        STATUS current
        DESCRIPTION
            "The port identifier(base 1) of the neighbor device, to which the local device connect."
        ::= { raisecomRndpDiscoveryEntry 3 }

    raisecomRndpDiscoveryHostName OBJECT-TYPE
        SYNTAX  OCTET STRING
        MAX-ACCESS read-only
        STATUS current
        DESCRIPTION
            "Remote device host name."
        ::= { raisecomRndpDiscoveryEntry 4 }

    raisecomRndpDiscoveryPlatformOid OBJECT-TYPE
        SYNTAX  OBJECT IDENTIFIER
        MAX-ACCESS read-only
        STATUS current
        DESCRIPTION
            "Remote device playform OID."
        ::= { raisecomRndpDiscoveryEntry 5 }

    raisecomRndpDiscoveryVersion OBJECT-TYPE
        SYNTAX  OCTET STRING
        MAX-ACCESS read-only
        STATUS current
        DESCRIPTION
            "Remote device software version."
        ::= { raisecomRndpDiscoveryEntry 6 }

    raisecomRndpDiscoveryCapabilities OBJECT-TYPE
        SYNTAX  INTEGER  {
                 switch(1),
                 router(2),
                 eoa(3),
                 eos(4),
                 others(5)
                }
        MAX-ACCESS read-only
        STATUS current
        DESCRIPTION
            "Remote device capabilities."
        ::= { raisecomRndpDiscoveryEntry 7 }

------------  raisecomRndpInterfaceTable   ----------------
    raisecomRndpInterfaceTable OBJECT-TYPE
        SYNTAX SEQUENCE OF RaisecomRndpInterfaceEntry
        MAX-ACCESS not-accessible
        STATUS mandatory
        DESCRIPTION
            "Rndp interface control table."
        ::= { raisecomTopoDiscovery 3 }

    raisecomRndpInterfaceEntry OBJECT-TYPE
        SYNTAX RaisecomRndpInterfaceEntry
        MAX-ACCESS not-accessible
        STATUS mandatory
        DESCRIPTION
            "Rndp interface control table entry."
        INDEX { raisecomRndpInterfaceId }
        ::= { raisecomRndpInterfaceTable 1 }

    RaisecomRndpInterfaceEntry ::= SEQUENCE {
        raisecomRndpInterfaceId            INTEGER,
        raisecomRndpInterfaceEnable        INTEGER
     }

    raisecomRndpInterfaceId OBJECT-TYPE
        SYNTAX INTEGER
        MAX-ACCESS read-only
        STATUS mandatory
        DESCRIPTION
            "An index based 1 that uniquely identifies a system interface."
        ::= { raisecomRndpInterfaceEntry 1 }

    raisecomRndpInterfaceEnable OBJECT-TYPE
        SYNTAX  EnableVar
        MAX-ACCESS read-write
        STATUS mandatory
        DESCRIPTION
            "DURABLE: { enable }
            enable(1) or disable(2) raisecomRndp on this interface."
        ::= { raisecomRndpInterfaceEntry 2 }
END
