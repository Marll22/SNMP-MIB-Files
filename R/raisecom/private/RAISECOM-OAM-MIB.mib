--20120705,yangzhonghong,ESW00002626 去掉raisecomOamLostTrap的绑定变量: dot3OamPeerMacAddress与代码一致
--MibName=raisecomOamMIB
   RAISECOM-OAM-MIB DEFINITIONS ::= BEGIN 
   
    IMPORTS         
      MODULE-IDENTITY, OBJECT-TYPE, NOTIFICATION-TYPE
        									FROM SNMPv2-SMI 
        Dot3Oui,
        dot3OamPeerMacAddress,
        dot3OamPeerVendorOui,
        dot3OamPeerVendorInfo, 
        dot3OamEventLogOui, 
        dot3OamEventLogType,
        dot3OamEventLogLocation       		FROM  DOT3-OAM-MIB
      	ifIndex   			       			FROM IF-MIB      
      	oam									FROM RAISECOM-BASE-MIB
      	TimeStamp, TruthValue				FROM SNMPv2-TC; 

   
      raisecomOamMIB MODULE-IDENTITY 
        LAST-UPDATED "200609050000Z"  -- Sept 5,2006"
        ORGANIZATION 
          "raisecom"
        CONTACT-INFO 
          "          "
        DESCRIPTION
          "The MIB module for managing trap, notification and extension configure of oam."
   
        REVISION    "200609050000Z"  -- Sept 5, 2006"
        DESCRIPTION ""
     
         ::= { oam 2 }
      
      -- 
      -- Sections of the raisecom OAM MIB
      --
         raisecomOamObjects 			OBJECT IDENTIFIER ::= { raisecomOamMIB 1 }
         raisecomOamNotifications       OBJECT IDENTIFIER ::= { raisecomOamMIB 2 }   
        
      -- ***************************************************************
      --
      -- private OAM object group
      --
   
   
      raisecomOamTrapTable OBJECT-TYPE
        SYNTAX      SEQUENCE OF RaisecomOamTrapEntry
        MAX-ACCESS  not-accessible
        STATUS      current
        DESCRIPTION 
          "A table of OAM trap. "   
        ::= { raisecomOamObjects 1 }
   
      raisecomOamTrapEntry OBJECT-TYPE
        SYNTAX     RaisecomOamTrapEntry
        MAX-ACCESS not-accessible
        STATUS     current
        DESCRIPTION 
          "Table entry for OAM trap.    "
        INDEX       { ifIndex }
        ::= { raisecomOamTrapTable 1 }
   
      RaisecomOamTrapEntry ::=
        SEQUENCE {
          raisecomOamEventTrapEnable			TruthValue,
          raisecomOamPeerEventTrapEnable		TruthValue,
          raisecomOamDiscoveryTrapTotal			Unsigned32,
          raisecomOamDiscoveryTrapTimestamp     TimeStamp,
          raisecomOamLostTrapTotal              Unsigned32, 
          raisecomOamLostTrapTimestamp          TimeStamp
        }
   
              
      raisecomOamEventTrapEnable OBJECT-TYPE
        SYNTAX      TruthValue
        MAX-ACCESS  read-write
        STATUS      current
        DESCRIPTION 
          "Enable or disable trap for the local normal link events." 
         ::= { raisecomOamTrapEntry 1 }
   
      raisecomOamPeerEventTrapEnable OBJECT-TYPE
        SYNTAX    TruthValue  
        MAX-ACCESS  read-write
        STATUS      current
        DESCRIPTION 
          "Enable or disable trap for the peer normal link events. "
        ::= { raisecomOamTrapEntry 2 }
   
      raisecomOamDiscoveryTrapTotal OBJECT-TYPE
        SYNTAX      Unsigned32        
        MAX-ACCESS  read-only
        STATUS      current
        DESCRIPTION 
          "A running total of the number of times the discovery trap has occurred.  "
        ::= { raisecomOamTrapEntry 3 }
   
      raisecomOamDiscoveryTrapTimestamp OBJECT-TYPE
        SYNTAX      TimeStamp        
        MAX-ACCESS  read-only
        STATUS      current 
        DESCRIPTION 
          "A timestamp of the last discovery trap."
        ::= { raisecomOamTrapEntry 4 }  
        
      raisecomOamLostTrapTotal OBJECT-TYPE
        SYNTAX      Unsigned32        
        MAX-ACCESS  read-only
        STATUS      current
        DESCRIPTION 
          "A running total of the number of times the peer lost trap has occurred. "
        ::= { raisecomOamTrapEntry 5 }
   
      raisecomOamLostTrapTimestamp OBJECT-TYPE
        SYNTAX      TimeStamp        
        MAX-ACCESS  read-only
        STATUS      current 
        DESCRIPTION 
          "A timestamp of the last peer lost trap."
        ::= { raisecomOamTrapEntry 6 }
               
      -- ***************************************************************
      -- 
      -- remote management table
      -- 
             
                        
      raisecomOamRemoteMgtTable OBJECT-TYPE
        SYNTAX      SEQUENCE OF RaisecomOamRemoteMgtEntry
        MAX-ACCESS  not-accessible
        STATUS      current
        DESCRIPTION 
          "A table of OAM trap. "   
        ::= { raisecomOamObjects 2 }
   
      raisecomOamRemoteMgtEntry OBJECT-TYPE
        SYNTAX     RaisecomOamRemoteMgtEntry
        MAX-ACCESS not-accessible
        STATUS     current
        DESCRIPTION 
          "Table entry for OAM trap.    "
        INDEX       { ifIndex }
        ::= { raisecomOamRemoteMgtTable 1 }
   
      RaisecomOamRemoteMgtEntry ::=
        SEQUENCE {     
          raisecomOamRemoteMgtBranch	INTEGER,
          raisecomOamRemoteMgtLeaf		INTEGER,
          raisecomOamRemoteMgtValue		OCTET STRING,
          raisecomOamRemoteMgtStatus    INTEGER
        }   
              
      raisecomOamRemoteMgtBranch OBJECT-TYPE
        SYNTAX      INTEGER {
        	object(3), 
			package(4),    
        	attribute(7)
        }
        MAX-ACCESS  read-write
        STATUS      current
        DESCRIPTION 
          "Derived from the CMIP protocol encodings in Annex 30A, 
          Variable Branches may reference attributes, objects or packages." 
         ::= { raisecomOamRemoteMgtEntry 1 }                     
                      
      raisecomOamRemoteMgtLeaf OBJECT-TYPE
        SYNTAX      INTEGER  (1..65535)
        MAX-ACCESS  read-write
        STATUS      current
        DESCRIPTION 
          "The leaf is derived from the CMIP protocol encodings in Annex 30A" 
         ::= { raisecomOamRemoteMgtEntry 2 }         
                                             
      raisecomOamRemoteMgtValue OBJECT-TYPE
        SYNTAX      OCTET STRING  (SIZE(1..512))
        MAX-ACCESS  read-write
        STATUS      current
        DESCRIPTION 
          "A list of variable widths and values copyed from 
          IEEE802.3ah OAM variable container. It is valid only 
          when raisecomOamRemoteMgtStatus is 0. A single value 
          '0' means error occurred durning OAM mib-get. " 
         ::= { raisecomOamRemoteMgtEntry 3 } 
          
      raisecomOamRemoteMgtStatus OBJECT-TYPE
        SYNTAX INTEGER  {
               ok(0),
               wait(1), 
               get(2) 
        }
        MAX-ACCESS  read-write
        STATUS      current
        DESCRIPTION 
          "Status of OAM mib get." 
         ::= { raisecomOamRemoteMgtEntry 4 }       
         
     -- ***************************************************************
      -- 
      -- oam extension configure
      -- 
          raisecomOamExtensionCfg       OBJECT IDENTIFIER ::= { raisecomOamObjects 3 }
        
    
      raisecomOamTimeout OBJECT-TYPE
        SYNTAX      INTEGER  (1..50)
        MAX-ACCESS  read-write
        STATUS      current
        DESCRIPTION 
          "The OAM link timeout time in second." 
         ::= { raisecomOamExtensionCfg 1 }
                   
      raisecomOamSendPeriod OBJECT-TYPE
        SYNTAX      INTEGER  (1..100)        
        MAX-ACCESS  read-write
        STATUS      current
        DESCRIPTION 
          "The OAM message send period in 100ms.  "
        ::= { raisecomOamExtensionCfg 2 }
  
      -- ***************************************************************
      -- 
      -- private OAM Notifications
      -- 
   
   
      raisecomOamDiscoveryTrap NOTIFICATION-TYPE
        OBJECTS { ifIndex,
            	dot3OamPeerMacAddress,
            	dot3OamPeerVendorOui,
            	dot3OamPeerVendorInfo
            	}
        STATUS  current
        DESCRIPTION
          "OAM Discovery Trap"
       ::= { raisecomOamNotifications 1 } 
            
   
      raisecomOamLostTrap NOTIFICATION-TYPE
        OBJECTS {  
                  ifIndex
                }
        STATUS  current
        DESCRIPTION
          "The OAM peer lost."
       ::= { raisecomOamNotifications 2 }
          

      raisecomOamNormalTrap NOTIFICATION-TYPE
        OBJECTS {   dot3OamEventLogOui, 
                  dot3OamEventLogType,
                  dot3OamEventLogLocation
                }
        STATUS  current
        DESCRIPTION
          ""
       ::= { raisecomOamNotifications 3 }
   
      END
