--
-- ddm.mib
-- MIB generated by MG-SOFT Visual MIB Builder Version 6.0  Build 88
-- Friday, June 15, 2012 at 09:18:51
--

	QTECH-DDM-MIB DEFINITIONS ::= BEGIN
 
		IMPORTS
			Integer32, BITS, OBJECT-TYPE, MODULE-IDENTITY, NOTIFICATION-TYPE			
				FROM SNMPv2-SMI			
			TEXTUAL-CONVENTION			
				FROM SNMPv2-TC			
			qtechProducts, qtechProtocol, qtechMgmt			
				FROM QTECH-SMI;
	
	
		qtechDdm MODULE-IDENTITY 
			LAST-UPDATED "201206060945Z"		-- June 06, 2012 at 09:45 GMT
			ORGANIZATION 
				"FiberHome Networks Systems, Inc."
			CONTACT-INFO 
				"http://www.fhn.com.cn"
			DESCRIPTION 
				" The info of ddm module."
			::= { qtechMgmt 305 }

		
	
--
-- Textual conventions
--
	
		EntryStatus ::= TEXTUAL-CONVENTION
			STATUS current
			DESCRIPTION 
				"entry status."
			SYNTAX INTEGER
				{
				valid(1),
				createRequest(2),
				underCreation(3),
				invalid(4)
				}

		DisplayString ::= TEXTUAL-CONVENTION
			STATUS current
			DESCRIPTION 
				"8 bit octet."
			SYNTAX OCTET STRING

	
--
-- Node definitions
--
	
		ddmGeneral OBJECT IDENTIFIER ::= { qtechDdm 1 }

		
		ddmGeneralTrapEnable OBJECT-TYPE
			SYNTAX INTEGER
				{
				enable(1),
				disable(2)
				}
			MAX-ACCESS read-write
			STATUS current
			DESCRIPTION
				"Enable or disable the ddm trap."
			::= { ddmGeneral 1 }

		
		ddmInfoTable OBJECT-TYPE
			SYNTAX SEQUENCE OF DdmInfoEntry
			MAX-ACCESS not-accessible
			STATUS current
			DESCRIPTION
				"The info of ddm module."
			::= { qtechDdm 2 }

		
		ddmInfoEntry OBJECT-TYPE
			SYNTAX DdmInfoEntry
			MAX-ACCESS not-accessible
			STATUS current
			DESCRIPTION
				"The info of ddm module."
			INDEX { ddmInfoIndex }
			::= { ddmInfoTable 1 }

		
		DdmInfoEntry ::=
			SEQUENCE { 
				ddmInfoIndex
					Integer32,
				ddmInfoBias
					Integer32,
				ddmInfoHBias
					Integer32,
				ddmInfoLBias
					Integer32,
				ddmInfoVoltage
					Integer32,
				ddmInfoHVoltage
					Integer32,
				ddmInfoLVoltage
					Integer32,
				ddmInfoTemperature
					Integer32,
				ddmInfoHTemperature
					Integer32,
				ddmInfoLTemperature
					Integer32,
				ddmInfoRxpower
					Integer32,
				ddmInfoHRxpower
					Integer32,
				ddmInfoLRxpower
					Integer32,
				ddmInfoTxpower
					Integer32,
				ddmInfoHTxpower
					Integer32,
				ddmInfoLTxpower
					Integer32,
				ddmInfoTransceiver
					Integer32,
				ddmInfoIdentifier
					Integer32,
				ddmInfoConnector
					Integer32,
				ddmInfoWavelength
					Integer32,
				ddmInfoLinklength
					Integer32,
				ddmInfoEncoding
					Integer32,
				ddmInfoNominalBr
					Integer32,
				ddmInfoMinBr
					Integer32,
				ddmInfoMaxBr
					Integer32,
				ddmInfoTxFault
					INTEGER,
				ddmInfoTxDisable
					INTEGER,
				ddmInfoDDMSupport
					INTEGER,
				ddmInfoVendorName
					OCTET STRING,
				ddmInfoVendorPartNum
					OCTET STRING,
				ddmInfoVendorSerialNum
					OCTET STRING,
				ddmInfoVendorRevNum
					OCTET STRING,
				ddmInfoManufacturingDate
					OCTET STRING,
				ddmInfoTemperaureAutoLmt
					INTEGER,
				ddmInfoRxpowerAutoLmt
					INTEGER,
				ddmInfoTxpowerAutoLmt
					INTEGER,
				ddmInfoBiasAutoLmt
					INTEGER,
				ddmInfoVoltageAutoLmt
					INTEGER,
				ddmInfoRxLos
					INTEGER,
				ddmInfoWaring
					BITS,
				ddmInfoModulePresent
					INTEGER,
				ddmInfoDDMSupportFuns
					OCTET STRING,
				ddmInfoTransceiverType
					OCTET STRING,
				ddmInfoEncodingType
					OCTET STRING,
				ddmInfoDDMSupportFunsType
					OCTET STRING,
				ddmInfoPecCode
					OCTET STRING
			 }

		ddmInfoIndex OBJECT-TYPE
			SYNTAX Integer32
			MAX-ACCESS read-only
			STATUS current
			DESCRIPTION
				"The index of ddm table."
			::= { ddmInfoEntry 1 }

		
		ddmInfoBias OBJECT-TYPE
			SYNTAX Integer32
			MAX-ACCESS read-only
			STATUS current
			DESCRIPTION
				"The bias of laser  ."
			::= { ddmInfoEntry 2 }

		
		ddmInfoHBias OBJECT-TYPE
			SYNTAX Integer32
			MAX-ACCESS read-write
			STATUS current
			DESCRIPTION
				"The high  bias of laser."
			::= { ddmInfoEntry 3 }

		
		ddmInfoLBias OBJECT-TYPE
			SYNTAX Integer32
			MAX-ACCESS read-write
			STATUS current
			DESCRIPTION
				"The lower  bias of laser."
			::= { ddmInfoEntry 4 }

		
		ddmInfoVoltage OBJECT-TYPE
			SYNTAX Integer32
			MAX-ACCESS read-only
			STATUS current
			DESCRIPTION
				"The voltage of laser."
			::= { ddmInfoEntry 5 }

		
		ddmInfoHVoltage OBJECT-TYPE
			SYNTAX Integer32
			MAX-ACCESS read-write
			STATUS current
			DESCRIPTION
				"The high voltage of laser."
			::= { ddmInfoEntry 6 }

		
		ddmInfoLVoltage OBJECT-TYPE
			SYNTAX Integer32
			MAX-ACCESS read-write
			STATUS current
			DESCRIPTION
				"The lower voltage of laser."
			::= { ddmInfoEntry 7 }

		
		ddmInfoTemperature OBJECT-TYPE
			SYNTAX Integer32
			MAX-ACCESS read-only
			STATUS current
			DESCRIPTION
				"The temperature of laser."
			::= { ddmInfoEntry 8 }

		
		ddmInfoHTemperature OBJECT-TYPE
			SYNTAX Integer32
			MAX-ACCESS read-write
			STATUS current
			DESCRIPTION
				"The high temperature of laser."
			::= { ddmInfoEntry 9 }

		
		ddmInfoLTemperature OBJECT-TYPE
			SYNTAX Integer32
			MAX-ACCESS read-write
			STATUS current
			DESCRIPTION
				"The lower temperature of laser."
			::= { ddmInfoEntry 10 }

		
		ddmInfoRxpower OBJECT-TYPE
			SYNTAX Integer32
			MAX-ACCESS read-only
			STATUS current
			DESCRIPTION
				"The received power of laser."
			::= { ddmInfoEntry 11 }

		
		ddmInfoHRxpower OBJECT-TYPE
			SYNTAX Integer32
			MAX-ACCESS read-write
			STATUS current
			DESCRIPTION
				"The received high power of laser."
			::= { ddmInfoEntry 12 }

		
		ddmInfoLRxpower OBJECT-TYPE
			SYNTAX Integer32
			MAX-ACCESS read-write
			STATUS current
			DESCRIPTION
				"The received lower power of laser."
			::= { ddmInfoEntry 13 }

		
		ddmInfoTxpower OBJECT-TYPE
			SYNTAX Integer32
			MAX-ACCESS read-only
			STATUS current
			DESCRIPTION
				"The tranfer  power of laser."
			::= { ddmInfoEntry 14 }

		
		ddmInfoHTxpower OBJECT-TYPE
			SYNTAX Integer32
			MAX-ACCESS read-write
			STATUS current
			DESCRIPTION
				"The tranfer  high power of laser."
			::= { ddmInfoEntry 15 }

		
		ddmInfoLTxpower OBJECT-TYPE
			SYNTAX Integer32
			MAX-ACCESS read-write
			STATUS current
			DESCRIPTION
				"The tranfer lower power of laser."
			::= { ddmInfoEntry 16 }

		
		ddmInfoTransceiver OBJECT-TYPE
			SYNTAX Integer32
			MAX-ACCESS read-only
			STATUS current
			DESCRIPTION
				"The transceiver of laser."
			::= { ddmInfoEntry 17 }

		
		ddmInfoIdentifier OBJECT-TYPE
			SYNTAX Integer32
			MAX-ACCESS read-only
			STATUS current
			DESCRIPTION
				"The type of Identifier."
			::= { ddmInfoEntry 18 }

		
		ddmInfoConnector OBJECT-TYPE
			SYNTAX Integer32
			MAX-ACCESS read-only
			STATUS current
			DESCRIPTION
				"The connector of laser."
			::= { ddmInfoEntry 19 }

		
		ddmInfoWavelength OBJECT-TYPE
			SYNTAX Integer32
			MAX-ACCESS read-only
			STATUS current
			DESCRIPTION
				"The wave length  of laser."
			::= { ddmInfoEntry 20 }

		
		ddmInfoLinklength OBJECT-TYPE
			SYNTAX Integer32
			MAX-ACCESS read-only
			STATUS current
			DESCRIPTION
				"The link length  of laser."
			::= { ddmInfoEntry 21 }

		
		ddmInfoEncoding OBJECT-TYPE
			SYNTAX Integer32
			MAX-ACCESS read-only
			STATUS current
			DESCRIPTION
				"The encoding  of laser."
			::= { ddmInfoEntry 22 }

		
		ddmInfoNominalBr OBJECT-TYPE
			SYNTAX Integer32
			MAX-ACCESS read-only
			STATUS current
			DESCRIPTION
				"The nominal signalling rate  of laser."
			::= { ddmInfoEntry 23 }

		
		ddmInfoMinBr OBJECT-TYPE
			SYNTAX Integer32
			MAX-ACCESS read-only
			STATUS current
			DESCRIPTION
				"The lower bit rate margin of laser."
			::= { ddmInfoEntry 24 }

		
		ddmInfoMaxBr OBJECT-TYPE
			SYNTAX Integer32
			MAX-ACCESS read-only
			STATUS current
			DESCRIPTION
				"The high bit rate margin of laser."
			::= { ddmInfoEntry 25 }

		
		ddmInfoTxFault OBJECT-TYPE
			SYNTAX INTEGER
				{
				no(0),
				yes(1)
				}
			MAX-ACCESS read-only
			STATUS current
			DESCRIPTION
				"The fault status  of laser transfer."
			::= { ddmInfoEntry 26 }

		
		ddmInfoTxDisable OBJECT-TYPE
			SYNTAX INTEGER
				{
				no(0),
				yes(1)
				}
			MAX-ACCESS read-only
			STATUS current
			DESCRIPTION
				"The enable or disable  of laser transfer."
			::= { ddmInfoEntry 27 }

		
		ddmInfoDDMSupport OBJECT-TYPE
			SYNTAX INTEGER
				{
				no(0),
				yes(1)
				}
			MAX-ACCESS read-only
			STATUS current
			DESCRIPTION
				"The support or no support laser ."
			::= { ddmInfoEntry 28 }

		
		ddmInfoVendorName OBJECT-TYPE
			SYNTAX OCTET STRING (SIZE (0..1024))
			MAX-ACCESS read-only
			STATUS current
			DESCRIPTION
				"Vendor name ."
			::= { ddmInfoEntry 29 }

		
		ddmInfoVendorPartNum OBJECT-TYPE
			SYNTAX OCTET STRING (SIZE (0..1024))
			MAX-ACCESS read-only
			STATUS current
			DESCRIPTION
				"Vendor part name ."
			::= { ddmInfoEntry 30 }

		
		ddmInfoVendorSerialNum OBJECT-TYPE
			SYNTAX OCTET STRING (SIZE (0..1024))
			MAX-ACCESS read-only
			STATUS current
			DESCRIPTION
				"Vendor serial name ."
			::= { ddmInfoEntry 31 }

		
		ddmInfoVendorRevNum OBJECT-TYPE
			SYNTAX OCTET STRING (SIZE (0..1024))
			MAX-ACCESS read-only
			STATUS current
			DESCRIPTION
				"Revision level for part number ."
			::= { ddmInfoEntry 32 }

		
		ddmInfoManufacturingDate OBJECT-TYPE
			SYNTAX OCTET STRING (SIZE (0..1024))
			MAX-ACCESS read-only
			STATUS current
			DESCRIPTION
				"Vendor’s manufacturing date code ."
			::= { ddmInfoEntry 33 }

		
		ddmInfoTemperaureAutoLmt OBJECT-TYPE
			SYNTAX INTEGER
				{
				auto(1),
				userset(2)
				}
			MAX-ACCESS read-write
			STATUS current
			DESCRIPTION
				"The auto limt of temperature ."
			::= { ddmInfoEntry 34 }

		
		ddmInfoRxpowerAutoLmt OBJECT-TYPE
			SYNTAX INTEGER
				{
				auto(1),
				userset(2)
				}
			MAX-ACCESS read-write
			STATUS current
			DESCRIPTION
				"The auto limt of received power ."
			::= { ddmInfoEntry 35 }

		
		ddmInfoTxpowerAutoLmt OBJECT-TYPE
			SYNTAX INTEGER
				{
				auto(1),
				userset(2)
				}
			MAX-ACCESS read-write
			STATUS current
			DESCRIPTION
				"The auto limt of transfered power ."
			::= { ddmInfoEntry 36 }

		
		ddmInfoBiasAutoLmt OBJECT-TYPE
			SYNTAX INTEGER
				{
				auto(1),
				userset(2)
				}
			MAX-ACCESS read-write
			STATUS current
			DESCRIPTION
				"The auto limt of bias ."
			::= { ddmInfoEntry 37 }

		
		ddmInfoVoltageAutoLmt OBJECT-TYPE
			SYNTAX INTEGER
				{
				auto(1),
				userset(2)
				}
			MAX-ACCESS read-write
			STATUS current
			DESCRIPTION
				"The auto limt of voltage ."
			::= { ddmInfoEntry 38 }

		
		ddmInfoRxLos OBJECT-TYPE
			SYNTAX INTEGER
			MAX-ACCESS read-only
			STATUS current
			DESCRIPTION
				"The rx los info ."
			::= { ddmInfoEntry 39 }

		
		ddmInfoWaring OBJECT-TYPE
			SYNTAX BITS
				{
				tempunderflow(0),
				tempoverflow(1),
				biasunderflow(2),
				biasoverflow(3),
				txpowerunderflow(4),
				txpoweroverflow(5),
				rxpowerunderflow(6),
				rxpoweroverflow(7),
				volunderflow(8),
				voloverflow(9),
				rxlos(10),
				txfault(11)
				}
			MAX-ACCESS read-only
			STATUS current
			DESCRIPTION
				"The waring info of ddm ."
			::= { ddmInfoEntry 40 }

		
		ddmInfoModulePresent OBJECT-TYPE
			SYNTAX INTEGER
				{
				present(1),
				absent(2)
				}
			MAX-ACCESS read-only
			STATUS current
			DESCRIPTION
				"The module present info."
			::= { ddmInfoEntry 41 }

		
		ddmInfoDDMSupportFuns OBJECT-TYPE
			SYNTAX OCTET STRING (SIZE (0..64))
			MAX-ACCESS read-only
			STATUS current
			DESCRIPTION
				"The support or no support temperature、bias、voltage、power."
			::= { ddmInfoEntry 42 }

		ddmInfoTransceiverType OBJECT-TYPE
			SYNTAX OCTET STRING (SIZE (0..64))
			MAX-ACCESS read-only
			STATUS current
			DESCRIPTION
				"The transceiver type of laser."
			::= { ddmInfoEntry 43 }
					
		ddmInfoEncodingType OBJECT-TYPE
			SYNTAX OCTET STRING (SIZE (0..64))
			MAX-ACCESS read-only
			STATUS current
			DESCRIPTION
				"The encoding type of laser."
			::= { ddmInfoEntry 44 }
			
		ddmInfoDDMSupportFunsType OBJECT-TYPE
			SYNTAX OCTET STRING (SIZE (0..64))
			MAX-ACCESS read-only
			STATUS current
			DESCRIPTION
				"The support or no support temperature、bias、voltage、power."
			::= { ddmInfoEntry 45 }
			
		ddmInfoPecCode OBJECT-TYPE
			SYNTAX OCTET STRING (SIZE (0..64))
			MAX-ACCESS read-only
			STATUS current
			DESCRIPTION
				"PEC Code."
			::= { ddmInfoEntry 46 }
		
		ddmTraps OBJECT IDENTIFIER ::= { qtechDdm 3 }

		ddmTemperatureOverflow NOTIFICATION-TYPE
			OBJECTS { ddmInfoIndex, ddmInfoTemperature, ddmInfoHTemperature, ddmInfoLTemperature }
			STATUS current
			DESCRIPTION 
				"laser temperature over flow trap."
			::= { ddmTraps 1 }

		
		ddmTemperatureUnderflow NOTIFICATION-TYPE
			OBJECTS { ddmInfoIndex, ddmInfoTemperature, ddmInfoHTemperature, ddmInfoLTemperature }
			STATUS current
			DESCRIPTION 
				"laser temperature under flow trap."
			::= { ddmTraps 2 }

		
		ddmTemperatureOk NOTIFICATION-TYPE
			OBJECTS { ddmInfoIndex, ddmInfoTemperature, ddmInfoHTemperature, ddmInfoLTemperature }
			STATUS current
			DESCRIPTION 
				"laser temperature flow ok trap."
			::= { ddmTraps 3 }

		
		ddmRxpowerOverflow NOTIFICATION-TYPE
			OBJECTS { ddmInfoIndex, ddmInfoRxpower, ddmInfoHRxpower, ddmInfoLRxpower }
			STATUS current
			DESCRIPTION 
				"laser rx-power over flow trap."
			::= { ddmTraps 4 }

		
		ddmRxpowerUnderflow NOTIFICATION-TYPE
			OBJECTS { ddmInfoIndex, ddmInfoRxpower, ddmInfoHRxpower, ddmInfoLRxpower }
			STATUS current
			DESCRIPTION 
				"laser rx-power under flow trap."
			::= { ddmTraps 5 }

		
		ddmRxpowerOk NOTIFICATION-TYPE
			OBJECTS { ddmInfoIndex, ddmInfoRxpower, ddmInfoHRxpower, ddmInfoLRxpower }
			STATUS current
			DESCRIPTION 
				"laser rx-power flow ok trap."
			::= { ddmTraps 6 }

		
		ddmTxpowerOverflow NOTIFICATION-TYPE
			OBJECTS { ddmInfoIndex, ddmInfoTxpower, ddmInfoHTxpower, ddmInfoLTxpower }
			STATUS current
			DESCRIPTION 
				"laser tx-power over flow trap."
			::= { ddmTraps 7 }

		
		ddmTxpowerUnderflow NOTIFICATION-TYPE
			OBJECTS { ddmInfoIndex, ddmInfoTxpower, ddmInfoHTxpower, ddmInfoLTxpower }
			STATUS current
			DESCRIPTION 
				"laser tx-power under flow trap."
			::= { ddmTraps 8 }

		
		ddmTxpowerOk NOTIFICATION-TYPE
			OBJECTS { ddmInfoIndex, ddmInfoTxpower, ddmInfoHTxpower, ddmInfoLTxpower }
			STATUS current
			DESCRIPTION 
				"laser tx-power flow ok trap."
			::= { ddmTraps 9 }

		
		ddmVoltageOverflow NOTIFICATION-TYPE
			OBJECTS { ddmInfoIndex, ddmInfoVoltage, ddmInfoHVoltage, ddmInfoLVoltage }
			STATUS current
			DESCRIPTION 
				"laser voltage over flow trap."
			::= { ddmTraps 10 }

		
		ddmVoltageUnderflow NOTIFICATION-TYPE
			OBJECTS { ddmInfoIndex, ddmInfoVoltage, ddmInfoHVoltage, ddmInfoLVoltage }
			STATUS current
			DESCRIPTION 
				"laser voltage under flow trap."
			::= { ddmTraps 11 }

		
		ddmVoltageOk NOTIFICATION-TYPE
			OBJECTS { ddmInfoIndex, ddmInfoVoltage, ddmInfoHVoltage, ddmInfoLVoltage }
			STATUS current
			DESCRIPTION 
				"laser voltage flow ok trap."
			::= { ddmTraps 12 }

		
		ddmBiasCurrentOverflow NOTIFICATION-TYPE
			OBJECTS { ddmInfoIndex, ddmInfoBias, ddmInfoHBias, ddmInfoLBias }
			STATUS current
			DESCRIPTION 
				"laser voltage over flow trap."
			::= { ddmTraps 13 }

		
		ddmBiasCurrentUnderflow NOTIFICATION-TYPE
			OBJECTS { ddmInfoIndex, ddmInfoBias, ddmInfoHBias, ddmInfoLBias }
			STATUS current
			DESCRIPTION 
				"laser voltage under flow trap."
			::= { ddmTraps 14 }

		
		ddmBiasCurrentOk NOTIFICATION-TYPE
			OBJECTS { ddmInfoIndex, ddmInfoBias, ddmInfoHBias, ddmInfoLBias }
			STATUS current
			DESCRIPTION 
				"laser voltage flow ok trap."
			::= { ddmTraps 15 }

		
		ddmLaserSignalLos NOTIFICATION-TYPE
			OBJECTS { ddmInfoIndex }
			STATUS current
			DESCRIPTION 
				"Description."
			::= { ddmTraps 16 }

		
		ddmLaserSignalOk NOTIFICATION-TYPE
			OBJECTS { ddmInfoIndex }
			STATUS current
			DESCRIPTION 
				"Description."
			::= { ddmTraps 17 }

		
		ddmPlugIn NOTIFICATION-TYPE
			OBJECTS { ddmInfoIndex }
			STATUS current
			DESCRIPTION 
				"Description."
			::= { ddmTraps 18 }

		
		ddmPlugOut NOTIFICATION-TYPE
			OBJECTS { ddmInfoIndex }
			STATUS current
			DESCRIPTION 
				"Description."
			::= { ddmTraps 19 }

		
		ddmTxFault NOTIFICATION-TYPE
			OBJECTS { ddmInfoIndex }
			STATUS current
			DESCRIPTION 
				"Description."
			::= { ddmTraps 20 }

		
		ddmTxFaultOk NOTIFICATION-TYPE
			OBJECTS { ddmInfoIndex }
			STATUS current
			DESCRIPTION 
				"Description."
			::= { ddmTraps 21 }

		
	
	END

--
-- ddm.mib
--
