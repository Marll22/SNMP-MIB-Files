QTECH-G8032-MIB DEFINITIONS ::= BEGIN
 
		IMPORTS
			Integer32, Unsigned32, OBJECT-TYPE, NOTIFICATION-TYPE			
				FROM SNMPv2-SMI			
			TEXTUAL-CONVENTION			
				FROM SNMPv2-TC			
			qtechProducts, qtechProtocol			
				FROM QTECH-SMI;
	
	
--
-- Type definitions
--
	
--  Type definitions
-- 
-- Type definitions
-- 
-- Type definitions
-- 
-- Type definitions
-- 
		DisplayString ::= OCTET STRING

	
--
-- Textual conventions
--
	
--  Textual conventions
-- 
-- Textual conventions
-- 
-- Textual conventions
-- 
-- Textual conventions
-- 
		EntryStatus ::= TEXTUAL-CONVENTION
			STATUS current
			DESCRIPTION 
				"entry status."
			SYNTAX INTEGER
				{
				valid(1),
				createRequest(2),
				underCreation(3),
				invalid(4)
				}

	
--
-- Node definitions
--
	
--  Node definitions
-- 
-- Node definitions
-- 
-- Node definitions
-- 
-- Node definitions
-- 
		qtechG8032 OBJECT IDENTIFIER ::= { qtechProtocol 702 }

		
		g8032General OBJECT IDENTIFIER ::= { qtechG8032 1 }

		
		g8032NodeIsolationAvoid OBJECT-TYPE
			SYNTAX INTEGER
				{
				disable(2),
				enable(1)
				}
			MAX-ACCESS read-write
			STATUS current
			DESCRIPTION
				"node-isolation-avoid enable or disalbe"
			::= { g8032General 1 }

		
		g8032SubLoopAvoid OBJECT-TYPE
			SYNTAX INTEGER
				{
				disable(2),
				enable(1)
				}
			MAX-ACCESS read-write
			STATUS current
			DESCRIPTION
				"sub-ring loop avoid enable or disable"
			::= { g8032General 2 }

		
		g8032CcCheckTimer OBJECT-TYPE
			SYNTAX INTEGER
			MAX-ACCESS read-write
			STATUS current
			DESCRIPTION
				"cc check timer,unit is s"
			::= { g8032General 3 }

		
		g8032TrapEnable OBJECT-TYPE
			SYNTAX INTEGER
				{
				enable(1),
				disable(2)
				}
			MAX-ACCESS read-write
			STATUS current
			DESCRIPTION
				"Description."
			::= { g8032General 4 }

		
		g8032Y1731Auto OBJECT-TYPE
			SYNTAX INTEGER
				{
				enable(1),
				disable(2)
				}
			MAX-ACCESS read-write
			STATUS current
			DESCRIPTION
				"Description."
			::= { g8032General 5 }

		
		g8032VsSwitch OBJECT-TYPE
			SYNTAX INTEGER
				{
				enable(1),
				disable(2)
				}
			MAX-ACCESS read-write
			STATUS current
			DESCRIPTION
				"Description."
			::= { g8032General 6 }

		
		g8032InstanceTable OBJECT-TYPE
			SYNTAX SEQUENCE OF G8032InstanceEntry
			MAX-ACCESS not-accessible
			STATUS current
			DESCRIPTION
				"The list of configured ethernet  protection  switching
				instances."
			::= { qtechG8032 2 }

		
		g8032InstanceEntry OBJECT-TYPE
			SYNTAX G8032InstanceEntry
			MAX-ACCESS not-accessible
			STATUS current
			DESCRIPTION
				"A table entry representing each ethernet  protection  switching
				instance."
			INDEX { g8032InstanceIndex }
			::= { g8032InstanceTable 1 }

		
		G8032InstanceEntry ::=
			SEQUENCE { 
				g8032InstanceIndex
					Unsigned32,
				g8032InstanceVlanList
					OCTET STRING,
				g8032InstanceVlanAdd
					OCTET STRING,
				g8032InstanceVlanDel
					OCTET STRING,
				g8032InstanceCtrlVlan
					INTEGER,
				g8032InstanceVCVlan
					INTEGER,
				g8032InstanceVCOperStatus
					INTEGER,
				g8032InstanceWTRTimer
					INTEGER,
				g8032InstanceHoldOffTimer
					INTEGER,
				g8032InstanceGuardTimer
					INTEGER,
				g8032InstanceRole
					INTEGER,
				g8032InstanceRPLPort
					INTEGER,
				g8032InstancePort1
					INTEGER,
				g8032InstancePort1OperStatus
					INTEGER,
				g8032InstancePort1ForwardStatus
					INTEGER,
				g8032InstancePort2
					INTEGER,
				g8032InstancePort2OperStatus
					INTEGER,
				g8032InstancePort2ForwardStatus
					INTEGER,
				g8032InstanceSMStatus
					INTEGER,
				g8032InstanceRevertive
					INTEGER,
				g8032InstanceEntryStatus
					INTEGER,
				g8032InstanceNodeId
					OCTET STRING,
				g8032InstanceMel
					Integer32,
				g8032InstanceVCMel
					Integer32,
				g8032InstanceVCMepPort
					Integer32,
				g8032InstanceVCHoldOffTimer
					Integer32,
				g8032InstanceMipPortList
					OCTET STRING,
				g8032InstanceMipProtAdd
					Integer32,
				g8032InstanceMipPortDel
					Integer32,
				g8032InstanceWtrReMain
					Integer32,
				g8032InstanceVersion
					INTEGER,
				g8032InstanceProtectMode
					INTEGER,
				g8032InstanceRequestPort
					INTEGER
			 }

		g8032InstanceIndex OBJECT-TYPE
			SYNTAX Unsigned32
			MAX-ACCESS read-only
			STATUS current
			DESCRIPTION
				"The unique ID of this Ethernet  protection  switching instance.
				This value SHALL be between 1 and g8032MaxId 
				inclusively."
			::= { g8032InstanceEntry 1 }

		
		g8032InstanceVlanList OBJECT-TYPE
			SYNTAX OCTET STRING
			MAX-ACCESS read-write
			STATUS current
			DESCRIPTION
				"instance Data vlan"
			::= { g8032InstanceEntry 2 }

		
		g8032InstanceVlanAdd OBJECT-TYPE
			SYNTAX OCTET STRING
			MAX-ACCESS read-write
			STATUS current
			DESCRIPTION
				"add Data vlan"
			::= { g8032InstanceEntry 3 }

		
		g8032InstanceVlanDel OBJECT-TYPE
			SYNTAX OCTET STRING
			MAX-ACCESS read-write
			STATUS current
			DESCRIPTION
				"delete Data vlan"
			::= { g8032InstanceEntry 4 }

		
		g8032InstanceCtrlVlan OBJECT-TYPE
			SYNTAX INTEGER
			MAX-ACCESS read-write
			STATUS current
			DESCRIPTION
				"channel"
			::= { g8032InstanceEntry 5 }

		
		g8032InstanceVCVlan OBJECT-TYPE
			SYNTAX INTEGER
			MAX-ACCESS read-write
			STATUS current
			DESCRIPTION
				"virtual-channel"
			::= { g8032InstanceEntry 6 }

		
		g8032InstanceVCOperStatus OBJECT-TYPE
			SYNTAX INTEGER
			MAX-ACCESS read-only
			STATUS current
			DESCRIPTION
				"virtual-channel operate status"
			::= { g8032InstanceEntry 7 }

		
		g8032InstanceWTRTimer OBJECT-TYPE
			SYNTAX INTEGER
			MAX-ACCESS read-write
			STATUS current
			DESCRIPTION
				"wtr timer,unit is min"
			::= { g8032InstanceEntry 8 }

		
		g8032InstanceHoldOffTimer OBJECT-TYPE
			SYNTAX INTEGER
			MAX-ACCESS read-write
			STATUS current
			DESCRIPTION
				"hold off timer,unit is ms"
			::= { g8032InstanceEntry 9 }

		
		g8032InstanceGuardTimer OBJECT-TYPE
			SYNTAX INTEGER
			MAX-ACCESS read-write
			STATUS current
			DESCRIPTION
				"guard timer ,unit is ms"
			::= { g8032InstanceEntry 10 }

		
		g8032InstanceRole OBJECT-TYPE
			SYNTAX INTEGER
				{
				rplOwnerNode(1),
				rplNode(2),
				none(3)
				}
			MAX-ACCESS read-write
			STATUS current
			DESCRIPTION
				"instance role"
			::= { g8032InstanceEntry 11 }

		
		g8032InstanceRPLPort OBJECT-TYPE
			SYNTAX INTEGER
			MAX-ACCESS read-write
			STATUS current
			DESCRIPTION
				"instance rpl port"
			::= { g8032InstanceEntry 12 }

		
		g8032InstancePort1 OBJECT-TYPE
			SYNTAX INTEGER
			MAX-ACCESS read-write
			STATUS current
			DESCRIPTION
				"instance port1"
			::= { g8032InstanceEntry 13 }

		
		g8032InstancePort1OperStatus OBJECT-TYPE
			SYNTAX INTEGER
			MAX-ACCESS read-only
			STATUS current
			DESCRIPTION
				"instance port1 operate status"
			::= { g8032InstanceEntry 14 }

		
		g8032InstancePort1ForwardStatus OBJECT-TYPE
			SYNTAX INTEGER
			MAX-ACCESS read-only
			STATUS current
			DESCRIPTION
				"instance port1 forward status"
			::= { g8032InstanceEntry 15 }

		
		g8032InstancePort2 OBJECT-TYPE
			SYNTAX INTEGER
			MAX-ACCESS read-write
			STATUS current
			DESCRIPTION
				"instance port2"
			::= { g8032InstanceEntry 16 }

		
		g8032InstancePort2OperStatus OBJECT-TYPE
			SYNTAX INTEGER
			MAX-ACCESS read-only
			STATUS current
			DESCRIPTION
				"instance port2 operate status"
			::= { g8032InstanceEntry 17 }

		
		g8032InstancePort2ForwardStatus OBJECT-TYPE
			SYNTAX INTEGER
			MAX-ACCESS read-only
			STATUS current
			DESCRIPTION
				"instance port2 forward status"
			::= { g8032InstanceEntry 18 }

		
		g8032InstanceSMStatus OBJECT-TYPE
			SYNTAX INTEGER
				{
				idle(1),
				protect(2),
				manualSwitch(3),
				forcedSwitch(4),
				pending(5)
				}
			MAX-ACCESS read-only
			STATUS current
			DESCRIPTION
				"instance sm status"
			::= { g8032InstanceEntry 19 }

		
		g8032InstanceRevertive OBJECT-TYPE
			SYNTAX INTEGER
			MAX-ACCESS read-write
			STATUS current
			DESCRIPTION
				"instance mode
				revertive or non-revertive"
			::= { g8032InstanceEntry 20 }

		
		g8032InstanceEntryStatus OBJECT-TYPE
			SYNTAX INTEGER
				{
				valid(1),
				createRequest(2),
				underCreation(3),
				invalid(4)
				}
			MAX-ACCESS read-write
			STATUS current
			DESCRIPTION
				"instance entry status."
			::= { g8032InstanceEntry 21 }

		
		g8032InstanceNodeId OBJECT-TYPE
			SYNTAX OCTET STRING
			MAX-ACCESS read-write
			STATUS current
			DESCRIPTION
				"Description."
			::= { g8032InstanceEntry 22 }

		
		g8032InstanceMel OBJECT-TYPE
			SYNTAX Integer32
			MAX-ACCESS read-write
			STATUS current
			DESCRIPTION
				"Description."
			::= { g8032InstanceEntry 23 }

		
		g8032InstanceVCMel OBJECT-TYPE
			SYNTAX Integer32
			MAX-ACCESS read-write
			STATUS current
			DESCRIPTION
				"Description."
			::= { g8032InstanceEntry 24 }

		
		g8032InstanceVCMepPort OBJECT-TYPE
			SYNTAX Integer32
			MAX-ACCESS read-write
			STATUS current
			DESCRIPTION
				"Description."
			::= { g8032InstanceEntry 25 }

		
		g8032InstanceVCHoldOffTimer OBJECT-TYPE
			SYNTAX Integer32
			MAX-ACCESS read-write
			STATUS current
			DESCRIPTION
				"Description."
			::= { g8032InstanceEntry 26 }

		
		g8032InstanceMipPortList OBJECT-TYPE
			SYNTAX OCTET STRING
			MAX-ACCESS read-only
			STATUS current
			DESCRIPTION
				"Description."
			::= { g8032InstanceEntry 27 }

		
		g8032InstanceMipProtAdd OBJECT-TYPE
			SYNTAX Integer32
			MAX-ACCESS read-write
			STATUS current
			DESCRIPTION
				"Description."
			::= { g8032InstanceEntry 28 }

		
		g8032InstanceMipPortDel OBJECT-TYPE
			SYNTAX Integer32
			MAX-ACCESS read-write
			STATUS current
			DESCRIPTION
				"Description."
			::= { g8032InstanceEntry 29 }

		
		g8032InstanceWtrReMain OBJECT-TYPE
			SYNTAX Integer32
			MAX-ACCESS read-only
			STATUS current
			DESCRIPTION
				"Description."
			::= { g8032InstanceEntry 30 }

		
		g8032InstanceVersion OBJECT-TYPE
			SYNTAX INTEGER
				{
				version1(1),
				version2(2)
				}
			MAX-ACCESS read-write
			STATUS current
			DESCRIPTION
				"Description."
			::= { g8032InstanceEntry 31 }

		
		g8032InstanceProtectMode OBJECT-TYPE
			SYNTAX INTEGER
				{
				force-switch(1),
				manual-switch(2),
				auto(3),
				clear(4)
				}
			MAX-ACCESS read-write
			STATUS current
			DESCRIPTION
				"Description."
			::= { g8032InstanceEntry 32 }

		
		g8032InstanceRequestPort OBJECT-TYPE
			SYNTAX INTEGER
				{
				port1(1),
				port2(2)
				}
			MAX-ACCESS read-write
			STATUS current
			DESCRIPTION
				"Description."
			::= { g8032InstanceEntry 34 }

		
		g8032Trap OBJECT IDENTIFIER ::= { qtechG8032 3 }

		
		g8032StatusChange NOTIFICATION-TYPE
			OBJECTS { g8032InstanceSMStatus, g8032InstancePort1, g8032InstancePort2, g8032InstancePort1ForwardStatus, g8032InstancePort2ForwardStatus
				 }
			STATUS current
			DESCRIPTION 
				"status changed of instance."
			::= { g8032Trap 1 }

		
		g8032InstancePortTable OBJECT-TYPE
			SYNTAX SEQUENCE OF G8032InstancePortEntry
			MAX-ACCESS not-accessible
			STATUS current
			DESCRIPTION
				"Description."
			::= { qtechG8032 4 }

		
		g8032InstancePortEntry OBJECT-TYPE
			SYNTAX G8032InstancePortEntry
			MAX-ACCESS not-accessible
			STATUS current
			DESCRIPTION
				"Description."
			INDEX { g8032InstancePortInsIdx, g8032InstancePortPortIdx }
			::= { g8032InstancePortTable 1 }

		
		G8032InstancePortEntry ::=
			SEQUENCE { 
				g8032InstancePortInsIdx
					Integer32,
				g8032InstancePortPortIdx
					Integer32,
				g8032InstancePortIfUnit
					Integer32,
				g8032InstancePortOperstate
					Integer32,
				g8032InstancePortFwdstate
					Integer32,
				g8032InstancePortType
					Integer32,
				g8032InstancePortRxcount
					Integer32,
				g8032InstancePortTxcount
					Integer32,
				g8032InstancePortEntryStatus
					Integer32,
				g8032InstancePortRole
					Integer32
			 }

		g8032InstancePortInsIdx OBJECT-TYPE
			SYNTAX Integer32
			MAX-ACCESS read-only
			STATUS current
			DESCRIPTION
				"Description."
			::= { g8032InstancePortEntry 1 }

		
		g8032InstancePortPortIdx OBJECT-TYPE
			SYNTAX Integer32
			MAX-ACCESS read-only
			STATUS current
			DESCRIPTION
				"Description."
			::= { g8032InstancePortEntry 2 }

		
		g8032InstancePortIfUnit OBJECT-TYPE
			SYNTAX Integer32
			MAX-ACCESS read-only
			STATUS current
			DESCRIPTION
				"Description."
			::= { g8032InstancePortEntry 3 }

		
		g8032InstancePortOperstate OBJECT-TYPE
			SYNTAX Integer32
			MAX-ACCESS read-only
			STATUS current
			DESCRIPTION
				"Description."
			::= { g8032InstancePortEntry 4 }

		
		g8032InstancePortFwdstate OBJECT-TYPE
			SYNTAX Integer32
			MAX-ACCESS read-only
			STATUS current
			DESCRIPTION
				"Description."
			::= { g8032InstancePortEntry 5 }

		
		g8032InstancePortType OBJECT-TYPE
			SYNTAX Integer32
			MAX-ACCESS read-only
			STATUS current
			DESCRIPTION
				"Description."
			::= { g8032InstancePortEntry 6 }

		
		g8032InstancePortRxcount OBJECT-TYPE
			SYNTAX Integer32
			MAX-ACCESS read-only
			STATUS current
			DESCRIPTION
				"Description."
			::= { g8032InstancePortEntry 7 }

		
		g8032InstancePortTxcount OBJECT-TYPE
			SYNTAX Integer32
			MAX-ACCESS read-only
			STATUS current
			DESCRIPTION
				"Description."
			::= { g8032InstancePortEntry 8 }

		
		g8032InstancePortEntryStatus OBJECT-TYPE
			SYNTAX Integer32
			MAX-ACCESS read-write
			STATUS current
			DESCRIPTION
				"Description."
			::= { g8032InstancePortEntry 9 }

		
		g8032InstancePortRole OBJECT-TYPE
			SYNTAX Integer32
			MAX-ACCESS read-write
			STATUS current
			DESCRIPTION
				"Description."
			::= { g8032InstancePortEntry 10 }

		
	
	END

--
-- qtechG8032.mib
--
