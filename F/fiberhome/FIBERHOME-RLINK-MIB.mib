QTECH-RLINK-MIB DEFINITIONS ::= BEGIN
 
		IMPORTS
			Integer32, OBJECT-TYPE,NOTIFICATION-TYPE
				FROM SNMPv2-SMI			
			qtechProtocol			
				FROM QTECH-SMI;
	
	
--
-- Node definitions
--
	
		wriRlink OBJECT IDENTIFIER ::= { qtechProtocol 1809 }

		
		-- 1.3.6.1.4.1.3807.2.1809.1
		wriRlinkGeneral OBJECT IDENTIFIER ::= { wriRlink 1 }

		
		-- 1.3.6.1.4.1.3807.2.1809.1.1
		wriRlinkGeneralIfCount OBJECT-TYPE
			SYNTAX Integer32
			MAX-ACCESS read-only
			STATUS current
			DESCRIPTION
				"Rlink max interface number."
			::= { wriRlinkGeneral 1 }

		
		-- 1.3.6.1.4.1.3807.2.1809.1.2
		wriRlinkGeneralIfFreeCount OBJECT-TYPE
			SYNTAX Integer32
			MAX-ACCESS read-only
			STATUS current
			DESCRIPTION
				"Rlink free interface number."
			::= { wriRlinkGeneral 2 }

		
		-- 1.3.6.1.4.1.3807.2.1809.1.3
		wriRlinkGeneralGroupCount OBJECT-TYPE
			SYNTAX Integer32
			MAX-ACCESS read-only
			STATUS current
			DESCRIPTION
				"Rlink max group number."
			::= { wriRlinkGeneral 3 }

		
		-- 1.3.6.1.4.1.3807.2.1809.1.4
		wriRlinkGeneralGroupFreeCount OBJECT-TYPE
			SYNTAX Integer32
			MAX-ACCESS read-only
			STATUS current
			DESCRIPTION
				"Rlink free group number."
			::= { wriRlinkGeneral 4 }

		
		-- 1.3.6.1.4.1.3807.2.1809.1.5
		wriRlinkGeneralMemberCount OBJECT-TYPE
			SYNTAX Integer32
			MAX-ACCESS read-only
			STATUS current
			DESCRIPTION
				"Rlink max member number."
			::= { wriRlinkGeneral 5 }

		
		-- 1.3.6.1.4.1.3807.2.1809.1.6
		wriRlinkGeneralMemberFreeCount OBJECT-TYPE
			SYNTAX Integer32
			MAX-ACCESS read-only
			STATUS current
			DESCRIPTION
				"Rlink free member number."
			::= { wriRlinkGeneral 6 }

		-- 1.3.6.1.4.1.3807.2.1809.1.7
		wriRlinkGeneralSwVersion OBJECT-TYPE
			SYNTAX OCTET STRING(SIZE(255))
			MAX-ACCESS read-only
			STATUS current
			DESCRIPTION
				"Rlink Software version."
			::= { wriRlinkGeneral 7 }

		-- 1.3.6.1.4.1.3807.2.1809.2
		wriRlinkGroupTable OBJECT-TYPE
			SYNTAX SEQUENCE OF WriRlinkGroupEntry
			MAX-ACCESS not-accessible
			STATUS current
			DESCRIPTION
				"Rlink group table."
			::= { wriRlink 2 }

		
		-- 1.3.6.1.4.1.3807.2.1809.2.1
		wriRlinkGroupEntry OBJECT-TYPE
			SYNTAX WriRlinkGroupEntry
			MAX-ACCESS not-accessible
			STATUS current
			DESCRIPTION
				"Rlink group entry."
			INDEX { wriRlinkGroupIndex }
			::= { wriRlinkGroupTable 1 }

		
		WriRlinkGroupEntry ::=
			SEQUENCE { 
				wriRlinkGroupIndex
					Integer32,
				wriRlinkGroupEntryStatus
					INTEGER,
				wriRlinkGroupType
					INTEGER,
				wriRlinkGroupVlanList
					OCTET STRING,
				wriRlinkGroupDelVlanList
					OCTET STRING,
				wriRlinkGroupReverse
					INTEGER,
				wriRlinkGroupReverseTime
					Integer32,
				wriRlinkGroupRcvTimeout
					Integer32,
				wriRlinkGroupSendInterval
					Integer32,
				wriRlinkGroupManualChg
					Integer32,
				wriRlinkGroupPeerExisted
					INTEGER,
				wriRlinkGroupPeerMac
					OCTET STRING,
				wriRlinkGroupPeerRole
					INTEGER,
				wriRlinkGroupPeerState
					INTEGER,
				wriRlinkGroupPeerReverseTag
					INTEGER,
				wriRlinkGroupPeerSendInterval
					Integer32,
				wriRlinkGroupPeerLinkState
					INTEGER,
				wriRlinkGroupTrapEnable
				  INTEGER
			 }

		-- 1.3.6.1.4.1.3807.2.1809.2.1.1
		wriRlinkGroupIndex OBJECT-TYPE
			SYNTAX Integer32
			MAX-ACCESS read-only
			STATUS current
			DESCRIPTION
				"The group index of rlink group entry."
			::= { wriRlinkGroupEntry 1 }

		
		-- 1.3.6.1.4.1.3807.2.1809.2.1.2
		wriRlinkGroupEntryStatus OBJECT-TYPE
			SYNTAX INTEGER
				{
				valid(1),
				createrequest(2),
				undercreation(3),
				invalid(4)
				}
			MAX-ACCESS read-write
			STATUS current
			DESCRIPTION
				"The entry status of rlink group entry."
			::= { wriRlinkGroupEntry 2 }

		
		-- 1.3.6.1.4.1.3807.2.1809.2.1.3
		wriRlinkGroupType OBJECT-TYPE
			SYNTAX INTEGER
				{
				single(1),
				double(2)
				}
			MAX-ACCESS read-write
			STATUS current
			DESCRIPTION
				"Rlink group type."
			::= { wriRlinkGroupEntry 3 }

		
		-- 1.3.6.1.4.1.3807.2.1809.2.1.4
		wriRlinkGroupVlanList OBJECT-TYPE
			SYNTAX OCTET STRING
			MAX-ACCESS read-write
			STATUS current
			DESCRIPTION
				"Rlink group vlan list."
			::= { wriRlinkGroupEntry 4 }
		
		wriRlinkGroupDelVlanList OBJECT-TYPE
			SYNTAX OCTET STRING
			MAX-ACCESS read-write
			STATUS current
			DESCRIPTION
				"Rlink group delete vlan list."
			::= { wriRlinkGroupEntry 5 }
		
		-- 1.3.6.1.4.1.3807.2.1809.2.1.6
		wriRlinkGroupReverse OBJECT-TYPE
			SYNTAX INTEGER
				{
				enable(1),
				disable(0)
				}
			MAX-ACCESS read-write
			STATUS current
			DESCRIPTION
				"Whether or not the rlink group enabled reverse."
			::= { wriRlinkGroupEntry 6 }

		
		-- 1.3.6.1.4.1.3807.2.1809.2.1.7
		wriRlinkGroupReverseTime OBJECT-TYPE
			SYNTAX Integer32(3..60)
			MAX-ACCESS read-write
			STATUS current
			DESCRIPTION
				"Reverse time in second,if 'wriRlinkGroupReverse' is set 'enable',it effect."
			::= { wriRlinkGroupEntry 7 }

		
		-- 1.3.6.1.4.1.3807.2.1809.2.1.8
		wriRlinkGroupRcvTimeout OBJECT-TYPE
			SYNTAX Integer32(3..50)
			MAX-ACCESS read-write
			STATUS current
			DESCRIPTION
				"Receive-timeout is the multiple of send-interval."
			::= { wriRlinkGroupEntry 8 }

		
		-- 1.3.6.1.4.1.3807.2.1809.2.1.9
		wriRlinkGroupSendInterval OBJECT-TYPE
			SYNTAX Integer32(50..10000)
			MAX-ACCESS read-write
			STATUS current
			DESCRIPTION
				"Rlink group send-interval in milsecond."
			::= { wriRlinkGroupEntry 9 }

		
		-- 1.3.6.1.4.1.3807.2.1809.2.1.10
		wriRlinkGroupManualChg OBJECT-TYPE
			SYNTAX Integer32
			MAX-ACCESS read-write
			STATUS current
			DESCRIPTION
				"Rlink manual change."
			::= { wriRlinkGroupEntry 10 }

		
		-- 1.3.6.1.4.1.3807.2.1809.2.1.11
		wriRlinkGroupPeerExisted OBJECT-TYPE
			SYNTAX INTEGER
				{
				existed(1),
				not-existed(0)
				}
			MAX-ACCESS read-only
			STATUS current
			DESCRIPTION
				"Is the peer side existed."
			::= { wriRlinkGroupEntry 11 }

		
		-- 1.3.6.1.4.1.3807.2.1809.2.1.12
		wriRlinkGroupPeerMac OBJECT-TYPE
			SYNTAX OCTET STRING
			MAX-ACCESS read-only
			STATUS current
			DESCRIPTION
				"Rlink group peer side mac-address."
			::= { wriRlinkGroupEntry 12 }

		
		-- 1.3.6.1.4.1.3807.2.1809.2.1.13
		wriRlinkGroupPeerRole OBJECT-TYPE
			SYNTAX INTEGER
				{
				master(0),
				slave(1),
				sender(2)
				}
			MAX-ACCESS read-only
			STATUS current
			DESCRIPTION
				"Rlink group peer side role."
			::= { wriRlinkGroupEntry 13 }

		
		-- 1.3.6.1.4.1.3807.2.1809.2.1.143
		wriRlinkGroupPeerState OBJECT-TYPE
			SYNTAX INTEGER
				{
				block(0),
				forward(1)
				}
			MAX-ACCESS read-only
			STATUS current
			DESCRIPTION
				"Rlink group peer side state."
			::= { wriRlinkGroupEntry 14 }

		
		-- 1.3.6.1.4.1.3807.2.1809.2.1.15
		wriRlinkGroupPeerReverseTag OBJECT-TYPE
			SYNTAX INTEGER
				{
				enable(1),
				disable(2)
				}
			MAX-ACCESS read-only
			STATUS current
			DESCRIPTION
				"Whether or not the rlink group peer side enabled reverse."
			::= { wriRlinkGroupEntry 15 }

		
		-- 1.3.6.1.4.1.3807.2.1809.2.1.16
		wriRlinkGroupPeerSendInterval OBJECT-TYPE
			SYNTAX Integer32
			MAX-ACCESS read-only
			STATUS current
			DESCRIPTION
				"Rlink group peer side send-interval."
			::= { wriRlinkGroupEntry 16 }

		
		-- 1.3.6.1.4.1.3807.2.1809.2.1.17
		wriRlinkGroupPeerLinkState OBJECT-TYPE
			SYNTAX INTEGER
				{
				up(1),
				down(2)
				}
			MAX-ACCESS read-only
			STATUS current
			DESCRIPTION
				"Rlink group peer side link state."
			::= { wriRlinkGroupEntry 17 }
			
		wriRlinkGroupTrapEnable OBJECT-TYPE
			SYNTAX INTEGER
				{
				enable(1),
				disable(0)
				}
			MAX-ACCESS read-write
			STATUS current
			DESCRIPTION
				"Whether or not the rlink group peer side enabled trap."
			::= { wriRlinkGroupEntry 18 }

		-- 1.3.6.1.4.1.3807.2.1809.3
		wriRlinkIfTable OBJECT-TYPE
			SYNTAX SEQUENCE OF WriRlinkIfEntry
			MAX-ACCESS not-accessible
			STATUS current
			DESCRIPTION
				"Description."
			::= { wriRlink 3 }

		
		-- 1.3.6.1.4.1.3807.2.1809.3.1
		wriRlinkIfEntry OBJECT-TYPE
			SYNTAX WriRlinkIfEntry
			MAX-ACCESS not-accessible
			STATUS current
			DESCRIPTION
				"Description."
			INDEX { wriRlinkIfIndex }
			::= { wriRlinkIfTable 1 }

		
		WriRlinkIfEntry ::=
			SEQUENCE { 
				wriRlinkIfIndex
					Integer32,
				wriRlinkIfLinkState
					INTEGER
			 }

		-- 1.3.6.1.4.1.3807.2.1809.3.1.1
		wriRlinkIfIndex OBJECT-TYPE
			SYNTAX Integer32
			MAX-ACCESS read-only
			STATUS current
			DESCRIPTION
				"Interface index of this entry."
			::= { wriRlinkIfEntry 1 }

		-- 1.3.6.1.4.1.3807.2.1809.3.1.3
		wriRlinkIfLinkState OBJECT-TYPE
			SYNTAX INTEGER
				{
				up(1),
				down(2)
				}
			MAX-ACCESS read-only
			STATUS current
			DESCRIPTION
				"Rlink interface link state."
			::= { wriRlinkIfEntry 3 }

		
		-- 1.3.6.1.4.1.3807.2.1809.4
		wriRlinkMemberTable OBJECT-TYPE
			SYNTAX SEQUENCE OF WriRlinkMemberEntry
			MAX-ACCESS not-accessible
			STATUS current
			DESCRIPTION
				"Description."
			::= { wriRlink 4 }

		
		-- 1.3.6.1.4.1.3807.2.1809.4.1
		wriRlinkMemberEntry OBJECT-TYPE
			SYNTAX WriRlinkMemberEntry
			MAX-ACCESS not-accessible
			STATUS current
			DESCRIPTION
				"Description."
			INDEX { wriRlinkMemberIfIndex, wriRlinkMemberGroupIndex }
			::= { wriRlinkMemberTable 1 }

		
		WriRlinkMemberEntry ::=
			SEQUENCE { 
				wriRlinkMemberIfIndex
					Integer32,
				wriRlinkMemberGroupIndex
					Integer32,
				wriRlinkMemberEntryStatus
					INTEGER,
				wriRlinkMemberRole
					INTEGER,
				wriRlinkMemberState
					INTEGER,
				wriRlinkMemberSendVid
					Integer32
			 }

		-- 1.3.6.1.4.1.3807.2.1809.4.1.1
		wriRlinkMemberIfIndex OBJECT-TYPE
			SYNTAX Integer32
			MAX-ACCESS read-only
			STATUS current
			DESCRIPTION
				"The interface index of this entry."
			::= { wriRlinkMemberEntry 1 }

		
		-- 1.3.6.1.4.1.3807.2.1809.4.1.2
		wriRlinkMemberGroupIndex OBJECT-TYPE
			SYNTAX Integer32
			MAX-ACCESS read-only
			STATUS current
			DESCRIPTION
				"The group index of this entry."
			::= { wriRlinkMemberEntry 2 }

		
		-- 1.3.6.1.4.1.3807.2.1809.4.1.3
		wriRlinkMemberEntryStatus OBJECT-TYPE
			SYNTAX INTEGER
				{
				valid(1),
				createRequest(2),
				underCreation(3),
				invalid(4)
				}
			MAX-ACCESS read-write
			STATUS current
			DESCRIPTION
				"Entrystatus of this entry."
			::= { wriRlinkMemberEntry 3 }

		
		-- 1.3.6.1.4.1.3807.2.1809.4.1.4
		wriRlinkMemberRole OBJECT-TYPE
			SYNTAX INTEGER
				{
				master(0),
				slave(1),
				sender(2)
				}
			MAX-ACCESS read-write
			STATUS current
			DESCRIPTION
				"Rlink member role."
			::= { wriRlinkMemberEntry 4 }

		
		-- 1.3.6.1.4.1.3807.2.1809.4.1.5
		wriRlinkMemberState OBJECT-TYPE
			SYNTAX INTEGER
				{
				block(0),
				forward(1)
				}
			MAX-ACCESS read-only
			STATUS current
			DESCRIPTION
				"Rlink member state."
			::= { wriRlinkMemberEntry 5 }

		
		-- 1.3.6.1.4.1.3807.2.1809.4.1.6
		wriRlinkMemberSendVid OBJECT-TYPE
			SYNTAX Integer32
			MAX-ACCESS read-write
			STATUS current
			DESCRIPTION
				"Rlink member send-vlan."
			::= { wriRlinkMemberEntry 6 }

		rlinkTrap			OBJECT IDENTIFIER ::=   {wriRlink 5}
		
		rlinkMasterConflictTrap NOTIFICATION-TYPE
       		OBJECTS {wriRlinkGroupIndex,wriRlinkGroupPeerRole}
       		STATUS  current
       		DESCRIPTION
               	"rlink group master conflict trap."
			::= { rlinkTrap 1}
			
		rlinkSlaveConflictTrap NOTIFICATION-TYPE
       		OBJECTS {wriRlinkGroupIndex,wriRlinkGroupPeerRole}
       		STATUS  current
       		DESCRIPTION
               	"rlink group slave conflict trap."
			::= { rlinkTrap 2}
		
		rlinkMemStateChangeTrap NOTIFICATION-TYPE
       		OBJECTS {wriRlinkMemberIfIndex,wriRlinkMemberGroupIndex,wriRlinkMemberState}
       		STATUS  current
       		DESCRIPTION
               	"rlink member state change."          
			::= { rlinkTrap 3}

	END

--
-- wriRlink.mib
--
