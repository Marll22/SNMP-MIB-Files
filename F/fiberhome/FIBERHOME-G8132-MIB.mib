QTECH-G8132-MIB DEFINITIONS ::= BEGIN
 
		IMPORTS
			TimeTicks, Integer32, Unsigned32, OBJECT-TYPE, NOTIFICATION-TYPE			
				FROM SNMPv2-SMI			
			TEXTUAL-CONVENTION			
				FROM SNMPv2-TC			
			qtechProducts, qtechProtocol			
				FROM QTECH-SMI;
		
--  Type definitions
-- 
		DisplayString ::= OCTET STRING
	
--  Textual conventions
-- 
		EntryStatus ::= TEXTUAL-CONVENTION
			STATUS current
			DESCRIPTION 
				"entry status."
			SYNTAX INTEGER
				{
				valid(1),
				createRequest(2),
				underCreation(3),
				invalid(4)
				}
--  Node definitions
-- 
		-- 1.3.6.1.4.1.3807.2.704
		qtechG8132 OBJECT IDENTIFIER ::= { qtechProtocol 704 }

		
		-- 1.3.6.1.4.1.3807.2.704.1
		g8132General OBJECT IDENTIFIER ::= { qtechG8132 1 }

		
		-- 1.3.6.1.4.1.3807.2.704.1.1
		g8132AdminState OBJECT-TYPE
			SYNTAX INTEGER{start(1),stop(2)}
			MAX-ACCESS read-write
			STATUS current
			DESCRIPTION
				"g8132 Admin State"
			::= { g8132General 1 }

		
			-- 1.3.6.1.4.1.3807.2.704.1.2
		g8132NodeID OBJECT-TYPE
			SYNTAX INTEGER(1..255)
			MAX-ACCESS read-write
			STATUS current
			DESCRIPTION
				"g8132 Admin State"
			::= { g8132General 2 }
					
		-- 1.3.6.1.4.1.3807.2.704.2
		g8132InstanceTable OBJECT-TYPE
			SYNTAX SEQUENCE OF G8132InstanceEntry
			MAX-ACCESS not-accessible
			STATUS current
			DESCRIPTION
				"The list of configured ethernet protection switching
				instances."
			::= { qtechG8132 2 }

		
		-- 1.3.6.1.4.1.3807.2.704.2.1
		g8132InstanceEntry OBJECT-TYPE
			SYNTAX G8132InstanceEntry
			MAX-ACCESS not-accessible
			STATUS current
			DESCRIPTION
				"A table entry representing each T-MPLS Shared Protection Ring 
				instance."
			INDEX { g8132InstanceIndex }
			::= { g8132InstanceTable 1 }

		
		G8132InstanceEntry ::=
			SEQUENCE { 
				g8132InstanceIndex
					INTEGER,
				g8132InstanceStatus
					EntryStatus,
				g8132InstanceMode
					INTEGER,
				g8132InstanceMapLearnState
					INTEGER,
				g8132InstanceMapSize
					INTEGER,
				g8132InstanceWestPort
					INTEGER,
				g8132InstanceEastPort
					INTEGER,
				g8132InstanceWestNodeListAdd
					OCTET STRING,
				g8132InstanceEastNodeListAdd
					OCTET STRING,
				g8132InstanceWestNodeListDel
					OCTET STRING,
				g8132InstanceEastNodeListDel
					OCTET STRING,
				g8132InstanceWestLocalRequest
					INTEGER,
				g8132InstanceEastLocalRequest
					INTEGER,
				g8132InstanceMapComplete
					INTEGER
			 }

		-- 1.3.6.1.4.1.3807.2.704.2.1.1
		g8132InstanceIndex OBJECT-TYPE
			SYNTAX INTEGER
			MAX-ACCESS read-only
			STATUS current
			DESCRIPTION               
				"instance index."
			::= { g8132InstanceEntry 1 }

		
		-- 1.3.6.1.4.1.3807.2.704.2.1.2
		g8132InstanceStatus OBJECT-TYPE
			SYNTAX EntryStatus
			MAX-ACCESS read-write
			STATUS current
			DESCRIPTION
				""
			::= { g8132InstanceEntry 2 }

		
		-- 1.3.6.1.4.1.3807.2.704.2.1.3
		g8132InstanceMode OBJECT-TYPE
			SYNTAX INTEGER{wrapping(1),steering(2)}
			MAX-ACCESS read-write
			STATUS current
			DESCRIPTION
				"Instance mode"
			::= { g8132InstanceEntry 3 }

		
		-- 1.3.6.1.4.1.3807.2.704.2.1.4
		g8132InstanceMapLearnState OBJECT-TYPE
			SYNTAX INTEGER{enable(1),disable(2)}
			MAX-ACCESS read-write
			STATUS current
			DESCRIPTION
				"Instance Map Learn State"
			::= { g8132InstanceEntry 4 }

		
		-- 1.3.6.1.4.1.3807.2.704.2.1.5
		g8132InstanceMapSize OBJECT-TYPE
			SYNTAX INTEGER(3..64)
			MAX-ACCESS read-write
			STATUS current
			DESCRIPTION
				"Instance Map Size"
			::= { g8132InstanceEntry 5 }

		
		-- 1.3.6.1.4.1.3807.2.704.2.1.6
		g8132InstanceWestPort OBJECT-TYPE
			SYNTAX INTEGER
			MAX-ACCESS read-write
			STATUS current
			DESCRIPTION
				"Instance West Port"
			::= { g8132InstanceEntry 6 }

		
		-- 1.3.6.1.4.1.3807.2.704.2.1.7
		g8132InstanceEastPort OBJECT-TYPE
			SYNTAX INTEGER
			MAX-ACCESS read-write
			STATUS current
			DESCRIPTION
				"Instance East Port"
			::= { g8132InstanceEntry 7 }

		
		-- 1.3.6.1.4.1.3807.2.704.2.1.8
		g8132InstanceWestNodeListAdd OBJECT-TYPE
			SYNTAX OCTET STRING
			MAX-ACCESS read-write
			STATUS current
			DESCRIPTION
				"Add west node list 
				    8bit        8bit       8bit        8bit 
				 --------------------------------------------------
				 |  nodeId  | distance |  nodeId  | distance | .... 
				 --------------------------------------------------"
			::= { g8132InstanceEntry 8 }

		
		-- 1.3.6.1.4.1.3807.2.704.2.1.9
		g8132InstanceEastNodeListAdd OBJECT-TYPE
			SYNTAX OCTET STRING
			MAX-ACCESS read-write
			STATUS current
			DESCRIPTION
				"Add east node list
				   8bit        8bit       8bit        8bit 
				 --------------------------------------------------
				 |  nodeId  | distance |  nodeId  | distance | .... 
				 --------------------------------------------------"
			::= { g8132InstanceEntry 9 }

		
		-- 1.3.6.1.4.1.3807.2.704.2.1.10
		g8132InstanceWestNodeListDel OBJECT-TYPE
			SYNTAX OCTET STRING
			MAX-ACCESS read-write
			STATUS current
			DESCRIPTION
				"delete west node list
				   8bit        8bit       8bit        8bit 
				 --------------------------------------------------
				 |  nodeId  | distance |  nodeId  | distance | .... 
				 --------------------------------------------------"
			::= { g8132InstanceEntry 10 }

		
		-- 1.3.6.1.4.1.3807.2.704.2.1.11
		g8132InstanceEastNodeListDel OBJECT-TYPE
			SYNTAX OCTET STRING
			MAX-ACCESS read-write
			STATUS current
			DESCRIPTION
				"delete east node list
				   8bit        8bit       8bit        8bit 
				 --------------------------------------------------
				 |  nodeId  | distance |  nodeId  | distance | .... 
				 --------------------------------------------------"
			::= { g8132InstanceEntry 11 }

		
		-- 1.3.6.1.4.1.3807.2.704.2.1.12
		g8132InstanceWestLocalRequest OBJECT-TYPE
			SYNTAX INTEGER{
			default(1),
			clear(2),
			request-expire(3),
			lockout-protection(4),
			lockout-working (5),
			force-switch(6),
			wtr-expire(7),
			recover(8),
			signal-fail(9),
			manual-switch(10),
			wtr(11),
			exercise(12),
			reverse(13),
			no-request(14),
			map-learn(15)
			}
			MAX-ACCESS read-write
			STATUS current
			DESCRIPTION
				"Instance West Local Request"
			::= { g8132InstanceEntry 12 }

		
		-- 1.3.6.1.4.1.3807.2.704.2.1.13
		g8132InstanceEastLocalRequest OBJECT-TYPE
			SYNTAX INTEGER{
			default(1),
			clear(2),
			request-expire(3),
			lockout-protection(4),
			lockout-working (5),
			force-switch(6),
			wtr-expire(7),
			recover(8),
			signal-fail(9),
			manual-switch(10),
			wtr(11),
			exercise(12),
			reverse(13),
			no-request(14),
			map-learn(15)
			}
			MAX-ACCESS read-write
			STATUS current
			DESCRIPTION
				"Instance East Local Request"
			::= { g8132InstanceEntry 13 }

		
		-- 1.3.6.1.4.1.3807.2.704.2.1.14
		g8132InstanceMapComplete OBJECT-TYPE
			SYNTAX INTEGER{false(0),true(1)}
			MAX-ACCESS read-only
			STATUS current
			DESCRIPTION
				"protecting port operate status"
			::= { g8132InstanceEntry 14 }

		
			
		-- 1.3.6.1.4.1.3807.2.704.3
		g8132InstanceIfTable OBJECT-TYPE
			SYNTAX     SEQUENCE OF G8132InstanceIfEntry
			MAX-ACCESS not-accessible
			STATUS current
			DESCRIPTION
				"Description."
			::= { qtechG8132 3 }

		
		-- 1.3.6.1.4.1.3807.2.704.3.1
		g8132InstanceIfEntry OBJECT-TYPE
			SYNTAX G8132InstanceIfEntry
			MAX-ACCESS not-accessible
			STATUS current
			DESCRIPTION
				"Description."
			INDEX { g8132InstanceIfInstanceIndex, g8132InstanceIfIndex}
			::= { g8132InstanceIfTable 1 }

		
		G8132InstanceIfEntry ::=
			SEQUENCE { 
				g8132InstanceIfInstanceIndex
					INTEGER,
				g8132InstanceIfIndex
					INTEGER,
				g8132InstanceIfDirection
					INTEGER,
				g8132InstanceIfNeighborID
					INTEGER,
				g8132InstanceIfLocalRequest
					INTEGER,
				g8132InstanceIfRemoteRequest
					INTEGER,
				g8132InstanceIfOtherRequest
					INTEGER,
				g8132InstanceIfExcuteRequest
					INTEGER,
				g8132InstanceIfSMState
					INTEGER,
				g8132InstanceIfStatus
				     EntryStatus	
		 }

		-- 1.3.6.1.4.1.3807.2.704.3.1.1
		g8132InstanceIfInstanceIndex OBJECT-TYPE
			SYNTAX INTEGER
			MAX-ACCESS read-only
			STATUS current
			DESCRIPTION
				"Description."
			::= { g8132InstanceIfEntry 1 }

		
		-- 1.3.6.1.4.1.3807.2.704.3.1.2
		g8132InstanceIfIndex OBJECT-TYPE
			SYNTAX INTEGER
			MAX-ACCESS read-only
			STATUS current
			DESCRIPTION
				"Description."
			::= { g8132InstanceIfEntry 2 }

		
		-- 1.3.6.1.4.1.3807.2.704.3.1.3
		g8132InstanceIfDirection OBJECT-TYPE
			SYNTAX INTEGER{east(0),west(1)}
			MAX-ACCESS read-only
			STATUS current
			DESCRIPTION
				"Description."
			::= { g8132InstanceIfEntry 3 }

		
		-- 1.3.6.1.4.1.3807.2.704.3.1.4
		g8132InstanceIfNeighborID OBJECT-TYPE
			SYNTAX INTEGER
			MAX-ACCESS read-only
			STATUS current
			DESCRIPTION
				"Description."
			::= { g8132InstanceIfEntry 4 }

		
		-- 1.3.6.1.4.1.3807.2.704.3.1.5
		g8132InstanceIfLocalRequest OBJECT-TYPE
			SYNTAX INTEGER{
			default(1),
			clear(2),
			request-expire(3),
			lockout-protection(4),
			lockout-working (5),
			force-switch(6),
			wtr-expire(7),
			recover(8),
			signal-fail(9),
			manual-switch(10),
			wtr(11),
			exercise(12),
			reverse(13),
			no-request(14),
			map-learn(15)
			}

			MAX-ACCESS read-only
			STATUS current
			DESCRIPTION
				"Description."
			::= { g8132InstanceIfEntry 5 }

		
		-- 1.3.6.1.4.1.3807.2.704.3.1.6
		g8132InstanceIfRemoteRequest OBJECT-TYPE
			SYNTAX INTEGER{
			default(1),
			clear(2),
			request-expire(3),
			lockout-protection(4),
			lockout-working (5),
			force-switch(6),
			wtr-expire(7),
			recover(8),
			signal-fail(9),
			manual-switch(10),
			wtr(11),
			exercise(12),
			reverse(13),
			no-request(14),
			map-learn(15)
			}

			MAX-ACCESS read-only
			STATUS current
			DESCRIPTION
				"Description."
			::= { g8132InstanceIfEntry 6 }

		
		-- 1.3.6.1.4.1.3807.2.704.3.1.7
		g8132InstanceIfOtherRequest OBJECT-TYPE
			SYNTAX INTEGER{
			default(1),
			clear(2),
			request-expire(3),
			lockout-protection(4),
			lockout-working (5),
			force-switch(6),
			wtr-expire(7),
			recover(8),
			signal-fail(9),
			manual-switch(10),
			wtr(11),
			exercise(12),
			reverse(13),
			no-request(14),
			map-learn(15)
			}

			MAX-ACCESS read-only
			STATUS current
			DESCRIPTION
				"Description."
			::= { g8132InstanceIfEntry 7 }

		
		-- 1.3.6.1.4.1.3807.2.704.3.1.8
		g8132InstanceIfExcuteRequest OBJECT-TYPE
			SYNTAX INTEGER{
			local(1),
			remote(2),
			other(3)
			}

			MAX-ACCESS read-only
			STATUS current
			DESCRIPTION
				"Description."
			::= { g8132InstanceIfEntry 8 }

		
		-- 1.3.6.1.4.1.3807.2.704.3.1.9
		g8132InstanceIfSMState OBJECT-TYPE
			SYNTAX INTEGER{
				idle(1),
				pass-through(2),
				switching-LP(3),	
				ilde-LW(4),
				switching-FS(5),
				switching-SF(6),
				switching-MS(7),
				switching-WTR(8),
				switching-EXER(9)		
			}
			MAX-ACCESS read-only
			STATUS current
			DESCRIPTION
				"Description."
			::= { g8132InstanceIfEntry 9 }  
			
			
	     g8132InstanceIfStatus OBJECT-TYPE
			SYNTAX EntryStatus
			MAX-ACCESS read-write
			STATUS current
			DESCRIPTION
				"Description."
			::= { g8132InstanceIfEntry 10 }  
			
					
	  -- 1.3.6.1.4.1.3807.2.704.4
		g8132ProtectTable OBJECT-TYPE
			SYNTAX SEQUENCE OF G8132ProtectEntry
			MAX-ACCESS not-accessible
			STATUS current
			DESCRIPTION
				"Description."
			::= { qtechG8132 4 }

		
		-- 1.3.6.1.4.1.3807.2.704.3.1
		g8132ProtectEntry OBJECT-TYPE
			SYNTAX G8132ProtectEntry
			MAX-ACCESS not-accessible
			STATUS current
			DESCRIPTION
				"Description."
			INDEX { g8132ProtectInstanceIndex,g8132ProtectWorkLspName}
			::= { g8132ProtectTable 1 }

		
		G8132ProtectEntry ::=
			SEQUENCE { 
				g8132ProtectInstanceIndex
					INTEGER, 
				g8132ProtectWorkLspName
					OCTET STRING,
				g8132ProtectWorkLSPDstNodeID
					INTEGER,
				g8132ProtectWorkLSPOutIfIndex
					INTEGER, 			
				g8132ProtectSwitchState
					INTEGER,  
				g8132ProtectProtectLspName
					OCTET STRING,		
				g8132ProtectStatus
				    EntryStatus,
				g8132ProtectWorkLSPSrcNodeID
					INTEGER,
				g8132ProtectBridgeState
					INTEGER				
			}

       -- 1.3.6.1.4.1.3807.2.704.4.1.1
		g8132ProtectInstanceIndex OBJECT-TYPE
			SYNTAX INTEGER
			MAX-ACCESS read-only
			STATUS current
			DESCRIPTION
				"Description."
			::= { g8132ProtectEntry 1 }
		
		-- 1.3.6.1.4.1.3807.2.704.4.1.2
		g8132ProtectWorkLspName OBJECT-TYPE
			SYNTAX OCTET STRING(SIZE(1..24)) 
			MAX-ACCESS read-only
			STATUS current
			DESCRIPTION
				"Description."
			::= { g8132ProtectEntry 2 }   
         
        					
		-- 1.3.6.1.4.1.3807.2.704.4.1.3
		g8132ProtectWorkLSPDstNodeID OBJECT-TYPE
			SYNTAX INTEGER 
			MAX-ACCESS read-write
			STATUS current
			DESCRIPTION
				"Description."    	
			::= { g8132ProtectEntry 3}
				
       -- 1.3.6.1.4.1.3807.2.704.4.1.4
		g8132ProtectWorkLSPOutIfIndex OBJECT-TYPE
			SYNTAX INTEGER 
			MAX-ACCESS read-only
			STATUS current
			DESCRIPTION
				"Description."
			::= { g8132ProtectEntry 4 }   

	 -- 1.3.6.1.4.1.3807.2.704.4.1.5			
		g8132ProtectSwitchState	 OBJECT-TYPE
			SYNTAX INTEGER{false(0),true(1)} 
			MAX-ACCESS read-only
			STATUS current
			DESCRIPTION
				"Description."
			::= { g8132ProtectEntry 5 }     
			
	-- 1.3.6.1.4.1.3807.2.704.4.1.6					
		g8132ProtectProtectLspName	 OBJECT-TYPE
			SYNTAX OCTET STRING(SIZE(1..23)) 
			MAX-ACCESS read-write
			STATUS current
			DESCRIPTION
				"Description."
			::= { g8132ProtectEntry 6 }	
		
	 -- 1.3.6.1.4.1.3807.2.704.4.1.7			
		g8132ProtectStatus	 OBJECT-TYPE
			SYNTAX EntryStatus 
			MAX-ACCESS read-write
			STATUS current
			DESCRIPTION
				"Description."
			::= { g8132ProtectEntry 7 }	
	
	-- 1.3.6.1.4.1.3807.2.704.4.1.8		
		g8132ProtectWorkLSPSrcNodeID   OBJECT-TYPE
			SYNTAX INTEGER 
			MAX-ACCESS read-write
			STATUS current
			DESCRIPTION
				"Description."    	
			::= { g8132ProtectEntry 8}
		
	-- 1.3.6.1.4.1.3807.2.704.4.1.9			
		g8132ProtectBridgeState   OBJECT-TYPE
			SYNTAX INTEGER{false(0),true(1)} 
			MAX-ACCESS read-only
			STATUS current
			DESCRIPTION
				"Description."
			::= { g8132ProtectEntry 9 }
					
				     
			     		
	END

--
-- qtechg8132.mib
--
