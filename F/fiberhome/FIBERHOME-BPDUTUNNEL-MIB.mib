QTECH-BPDUTUNNEL-MIB DEFINITIONS ::= BEGIN
	IMPORTS
			MODULE-IDENTITY, OBJECT-TYPE, Counter32, Gauge32,
			Integer32,enterprises,NOTIFICATION-TYPE    FROM SNMPv2-SMI      	 
			TEXTUAL-CONVENTION,MacAddress			FROM SNMPv2-TC	
    		qtech,qtechProtocol			FROM QTECH-SMI;
		
		qtechBpduTunnel			OBJECT IDENTIFIER ::= { qtechProtocol 241 }

		qtechBpduTunnelMaxPort OBJECT-TYPE
			SYNTAX  INTEGER
			MAX-ACCESS  read-only
			STATUS  current
			DESCRIPTION
					"The max value of the interface that the protocol support."
			::= { qtechBpduTunnel 1 }
		
		qtechBpduTunnelMaxProtoPerPort  OBJECT-TYPE
			SYNTAX  INTEGER
			MAX-ACCESS  read-only
			STATUS  current
			DESCRIPTION
					"The max protocol num that every interface support."
			::= { qtechBpduTunnel 2 }

       
          -- The Bpdu Tunnel if Table
		qtechBpduTunnelIfTable OBJECT-TYPE
			SYNTAX  SEQUENCE OF QtechBpduTunnelIfEntry
			MAX-ACCESS  not-accessible
			STATUS  current
			DESCRIPTION
					"A table that contains port-specific information
					of Bpdu Tunnel."
			::= { qtechBpduTunnel 3}

		qtechBpduTunnelIfEntry OBJECT-TYPE
			SYNTAX  QtechBpduTunnelIfEntry
			MAX-ACCESS  not-accessible
			STATUS  current
			DESCRIPTION
					"A list of information maintained by every port
					about the Bpdu Tunnel state for that
					port."
			INDEX   { qtechBpduTunnelIfIndex }
			::= { qtechBpduTunnelIfTable 1 }

		QtechBpduTunnelIfEntry ::=
		SEQUENCE {
                  qtechBpduTunnelIfIndex		INTEGER,
                  qtechBpduTunnelIfState		INTEGER,
                  qtechBpduTunnelIfRole       INTEGER
                 }

		qtechBpduTunnelIfIndex OBJECT-TYPE
			SYNTAX      INTEGER 
			MAX-ACCESS  read-only
			STATUS  current
			DESCRIPTION
					"The port index."
			::= { qtechBpduTunnelIfEntry 1 }

		qtechBpduTunnelIfState OBJECT-TYPE
			SYNTAX  INTEGER{
				    enable(1),
				    disable(2)
			} 
			MAX-ACCESS  read-write
			STATUS  current
			DESCRIPTION
					"The state of interface."
		 ::= { qtechBpduTunnelIfEntry 2 }

		qtechBpduTunnelIfRole OBJECT-TYPE
			SYNTAX  INTEGER {
					uni(1),
					nni(2)					
				}
			MAX-ACCESS  read-write			
			STATUS  current
			DESCRIPTION
					"the role of interface."			
		::= { qtechBpduTunnelIfEntry 3 }


         -- The Bpdu Tunnel MAC Mapping Table
        qtechBpduTunnelMacTable OBJECT-TYPE
			SYNTAX  SEQUENCE OF QtechBpduTunnelMacEntry
			MAX-ACCESS  not-accessible
			STATUS   current
			DESCRIPTION
					"A table that contains mac mapping information 
					of Bpdu Tunnel."
			::= { qtechBpduTunnel 4}

		qtechBpduTunnelMacEntry OBJECT-TYPE
			SYNTAX  QtechBpduTunnelMacEntry
			MAX-ACCESS  not-accessible
			STATUS  current
			DESCRIPTION
					"A list of information of mac mapping iformation of Bpdu Tunnel.."
			INDEX   { qtechBpduTunnelIfIndex,qtechBpduTunnelProtocolMac }
			::= { qtechBpduTunnelMacTable 1 }

		QtechBpduTunnelMacEntry ::=
		SEQUENCE {
				  qtechBpduTunnelProtocolMac	   MacAddress,
                  qtechBpduTunnelProviderMac	   MacAddress,                  
                  qtechBpduTunnelMacRowStatus    INTEGER,
				  qtechBpduTunnelVid			   OCTET STRING
                 }

		qtechBpduTunnelProtocolMac OBJECT-TYPE
			SYNTAX  MacAddress
			MAX-ACCESS  read-only
			STATUS  current
			DESCRIPTION
				"The protocol mac address."
		 ::= { qtechBpduTunnelMacEntry 1 }


		qtechBpduTunnelProviderMac OBJECT-TYPE
			SYNTAX      MacAddress 
			MAX-ACCESS  read-write
			STATUS  current
			DESCRIPTION
				"The provider mac address."
			::= { qtechBpduTunnelMacEntry 2 }   
			

		qtechBpduTunnelMacRowStatus OBJECT-TYPE
			SYNTAX  INTEGER{
				valid (1),
				createRequest(2),
				underCreation(3),
				invalid(4)
			} 
			MAX-ACCESS  read-write			
			STATUS  current
			DESCRIPTION
				"The row status of mac address mapping."			
		::= { qtechBpduTunnelMacEntry 3 }
		
		qtechBpduTunnelVid OBJECT-TYPE
			SYNTAX OCTET STRING (SIZE(0..1024))
			MAX-ACCESS read-write
			STATUS current
			DESCRIPTION
				"The vlan id."
			::= { qtechBpduTunnelMacEntry 4}

		END
