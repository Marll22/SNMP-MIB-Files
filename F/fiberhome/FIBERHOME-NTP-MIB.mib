QTECH-NTP-MIB DEFINITIONS ::= BEGIN
 
		IMPORTS
			InetAddress			
				FROM INET-ADDRESS-MIB			
			Integer32, Unsigned32, Counter64, OBJECT-TYPE			
				FROM SNMPv2-SMI			
			qtechProtocol			
				FROM QTECH-SMI;
	
	
	
--
-- Node definitions
--
	
--  Node definitions
-- 
-- Node definitions
-- 
-- Node definitions
-- 
-- Node definitions
-- 
-- Node definitions
-- 
-- Node definitions
-- 
-- Node definitions
-- 
-- Node definitions
-- 
-- Node definitions
-- 
-- Node definitions
-- 
-- Node definitions
-- 
-- Node definitions
-- 
-- Node definitions
-- 
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1402
-- 1.3.6.1.4.1.3807.2.1406
		-- 1.3.6.1.4.1.3807.2.1406
		ntp OBJECT IDENTIFIER ::= { qtechProtocol 1406 }

		
--             1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1402.1
-- 1.3.6.1.4.1.3807.2.1406.1
		-- 1.3.6.1.4.1.3807.2.1406.1
		ntpCommon OBJECT IDENTIFIER ::= { ntp 1 }

		
--             1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1402.1.1
-- 1.3.6.1.4.1.3807.2.1406.1.1
		-- 1.3.6.1.4.1.3807.2.1406.1.1
		ntpClientSendInterval OBJECT-TYPE
			SYNTAX INTEGER (4..17)
			MAX-ACCESS read-write
			STATUS current
			DESCRIPTION
				"Description."
			::= { ntpCommon 1 }

		
--             1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1402.1.2
-- 1.3.6.1.4.1.3807.2.1406.1.2
		-- 1.3.6.1.4.1.3807.2.1406.1.2
		ntpServerSendInterval OBJECT-TYPE
			SYNTAX INTEGER (4..17)
			MAX-ACCESS read-write
			STATUS current
			DESCRIPTION
				"Description."
			::= { ntpCommon 2 }

		
--             1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1402.1.3
-- 1.3.6.1.4.1.3807.2.1406.1.3
		-- 1.3.6.1.4.1.3807.2.1406.1.3
		ntpStratum OBJECT-TYPE
			SYNTAX INTEGER (0..16)
			MAX-ACCESS read-write
			STATUS current
			DESCRIPTION
				"Description."
			::= { ntpCommon 3 }

		
--             1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1402.1.4
-- 1.3.6.1.4.1.3807.2.1406.1.4
		-- 1.3.6.1.4.1.3807.2.1406.1.4
		ntpMaster OBJECT-TYPE
			SYNTAX INTEGER
				{
				true(1),
				false(2)
				}
			MAX-ACCESS read-write
			STATUS current
			DESCRIPTION
				"Description."
			::= { ntpCommon 4 }

		
--             1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1402.1.5
-- 1.3.6.1.4.1.3807.2.1406.1.5
		-- 1.3.6.1.4.1.3807.2.1406.1.5
		ntpGlobalKeyId OBJECT-TYPE
			SYNTAX INTEGER
			MAX-ACCESS read-write
			STATUS current
			DESCRIPTION
				"Description."
			::= { ntpCommon 5 }

		
--             1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1402.1.6
-- 1.3.6.1.4.1.3807.2.1406.1.6
		-- 1.3.6.1.4.1.3807.2.1406.1.6
		ntpKeyGlobalStatus OBJECT-TYPE
			SYNTAX Integer32
			MAX-ACCESS read-write
			STATUS current
			DESCRIPTION
				"Description."
			::= { ntpCommon 6 }

		
--             1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1402.1.7
-- 1.3.6.1.4.1.3807.2.1406.1.7
		-- 1.3.6.1.4.1.3807.2.1406.1.7
		ntpKeyIdFreeIndex OBJECT-TYPE
			SYNTAX Integer32
			MAX-ACCESS read-only
			STATUS current
			DESCRIPTION
				"Description."
			::= { ntpCommon 7 }

		
--             1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1402.1.8
-- 1.3.6.1.4.1.3807.2.1406.1.8
		-- 1.3.6.1.4.1.3807.2.1406.1.8
		ntpPeerFreeIndex OBJECT-TYPE
			SYNTAX Integer32
			MAX-ACCESS read-only
			STATUS current
			DESCRIPTION
				"Description."
			::= { ntpCommon 8 }

		
--             1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1402.2
-- 1.3.6.1.4.1.3807.2.1406.2
		-- 1.3.6.1.4.1.3807.2.1406.2
		ntpKeyTable OBJECT-TYPE
			SYNTAX SEQUENCE OF NtpKeyEntry
			MAX-ACCESS not-accessible
			STATUS current
			DESCRIPTION
				"Description."
			::= { ntp 2 }

		
--             1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1402.2.1
-- 1.3.6.1.4.1.3807.2.1406.2.1
		-- 1.3.6.1.4.1.3807.2.1406.2.1
		ntpKeyEntry OBJECT-TYPE
			SYNTAX NtpKeyEntry
			MAX-ACCESS not-accessible
			STATUS current
			DESCRIPTION
				"Description."
			INDEX { ntpKeyId }
			::= { ntpKeyTable 1 }

		
		NtpKeyEntry ::=
			SEQUENCE { 
				ntpKeyId
					Unsigned32,
				ntpKeyString
					OCTET STRING,
				ntpKeyIdTrust
					INTEGER,
				ntpKeyEntryStatus
					Integer32
			 }

--             1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1402.2.1.1
-- 1.3.6.1.4.1.3807.2.1406.2.1.1
		-- 1.3.6.1.4.1.3807.2.1406.2.1.1
		ntpKeyId OBJECT-TYPE
			SYNTAX Unsigned32
			MAX-ACCESS read-only
			STATUS current
			DESCRIPTION
				"Description."
			::= { ntpKeyEntry 1 }

		
--             1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1402.2.1.2
-- 1.3.6.1.4.1.3807.2.1406.2.1.2
		-- 1.3.6.1.4.1.3807.2.1406.2.1.2
		ntpKeyString OBJECT-TYPE
			SYNTAX OCTET STRING
			MAX-ACCESS read-write
			STATUS current
			DESCRIPTION
				"Description."
			::= { ntpKeyEntry 2 }

		
--             1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1402.2.1.3
-- 1.3.6.1.4.1.3807.2.1406.2.1.3
		-- 1.3.6.1.4.1.3807.2.1406.2.1.3
		ntpKeyIdTrust OBJECT-TYPE
			SYNTAX INTEGER
				{
				true(1),
				false(2)
				}
			MAX-ACCESS read-write
			STATUS current
			DESCRIPTION
				"Description."
			::= { ntpKeyEntry 3 }

		
--             1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1402.2.1.4
-- 1.3.6.1.4.1.3807.2.1406.2.1.4
		-- 1.3.6.1.4.1.3807.2.1406.2.1.4
		ntpKeyEntryStatus OBJECT-TYPE
			SYNTAX Integer32
			MAX-ACCESS read-write
			STATUS current
			DESCRIPTION
				"Description."
			::= { ntpKeyEntry 4 }

		
--             1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1402.3
-- 1.3.6.1.4.1.3807.2.1406.3
		-- 1.3.6.1.4.1.3807.2.1406.3
		ntpPeerTable OBJECT-TYPE
			SYNTAX SEQUENCE OF NtpPeerEntry
			MAX-ACCESS not-accessible
			STATUS current
			DESCRIPTION
				"Description."
			::= { ntp 3 }

		
--             1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1402.3.1
-- 1.3.6.1.4.1.3807.2.1406.3.1
		-- 1.3.6.1.4.1.3807.2.1406.3.1
		ntpPeerEntry OBJECT-TYPE
			SYNTAX NtpPeerEntry
			MAX-ACCESS not-accessible
			STATUS current
			DESCRIPTION
				"Description."
			INDEX { ntpPeerIndex }
			::= { ntpPeerTable 1 }

		
		NtpPeerEntry ::=
			SEQUENCE { 
				ntpPeerIndex
					Integer32,
				ntpPeerWorkMode
					Integer32,
				ntpPeerAddrType
					Integer32,
				ntpPeerHostAddr
					InetAddress,
				ntpPeerPeerAddr
					InetAddress,
				ntpPeerVersion
					Integer32,
				ntpPeerKeyId
					Unsigned32,
				ntpPeerPort
					Integer32,
				ntpPeerEntryStatus
					Integer32,
				ntpPeerAssociationState
					Integer32,
				ntpPeerMulticastTtl
					Unsigned32,
				ntpPeerMulticastAddr
					InetAddress,
				ntpPeerStratum
					INTEGER,
				ntpPeerOffset
					OCTET STRING,
				ntpPeerDelay
					OCTET STRING,
				ntpPeerDispersion
					OCTET STRING,
				ntpPeerVrid
					INTEGER,
				--xf add 2014-9-29
				ntpPeerSourceInterface
					INTEGER
			 }

--             1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1402.3.1.1
-- 1.3.6.1.4.1.3807.2.1406.3.1.1
		-- 1.3.6.1.4.1.3807.2.1406.3.1.1
		ntpPeerIndex OBJECT-TYPE
			SYNTAX Integer32
			MAX-ACCESS read-only
			STATUS current
			DESCRIPTION
				"Description."
			::= { ntpPeerEntry 1 }

		
--             1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1402.3.1.2
-- 1.3.6.1.4.1.3807.2.1406.3.1.2
		-- 1.3.6.1.4.1.3807.2.1406.3.1.2
		ntpPeerWorkMode OBJECT-TYPE
			SYNTAX Integer32
			MAX-ACCESS read-write
			STATUS current
			DESCRIPTION
				"Description."
			::= { ntpPeerEntry 2 }

		
--             1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1402.3.1.3
-- 1.3.6.1.4.1.3807.2.1406.3.1.3
		-- 1.3.6.1.4.1.3807.2.1406.3.1.3
		ntpPeerAddrType OBJECT-TYPE
			SYNTAX Integer32
			MAX-ACCESS read-write
			STATUS current
			DESCRIPTION
				"Description."
			::= { ntpPeerEntry 3 }

		
--             1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1402.3.1.4
-- 1.3.6.1.4.1.3807.2.1406.3.1.4
		-- 1.3.6.1.4.1.3807.2.1406.3.1.4
		ntpPeerHostAddr OBJECT-TYPE
			SYNTAX InetAddress
			MAX-ACCESS read-write
			STATUS current
			DESCRIPTION
				"Description."
			::= { ntpPeerEntry 4 }

		
--             1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1402.3.1.5
-- 1.3.6.1.4.1.3807.2.1406.3.1.5
		-- 1.3.6.1.4.1.3807.2.1406.3.1.5
		ntpPeerPeerAddr OBJECT-TYPE
			SYNTAX InetAddress
			MAX-ACCESS read-write
			STATUS current
			DESCRIPTION
				"Description."
			::= { ntpPeerEntry 5 }

		
--             1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1402.3.1.6
-- 1.3.6.1.4.1.3807.2.1406.3.1.6
		-- 1.3.6.1.4.1.3807.2.1406.3.1.6
		ntpPeerVersion OBJECT-TYPE
			SYNTAX Integer32
			MAX-ACCESS read-write
			STATUS current
			DESCRIPTION
				"Description."
			::= { ntpPeerEntry 6 }

		
--             1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1402.3.1.7
-- 1.3.6.1.4.1.3807.2.1406.3.1.7
		-- 1.3.6.1.4.1.3807.2.1406.3.1.7
		ntpPeerKeyId OBJECT-TYPE
			SYNTAX Unsigned32
			MAX-ACCESS read-write
			STATUS current
			DESCRIPTION
				"Description."
			::= { ntpPeerEntry 7 }

		
--             1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1402.3.1.8
-- 1.3.6.1.4.1.3807.2.1406.3.1.8
		-- 1.3.6.1.4.1.3807.2.1406.3.1.8
		ntpPeerPort OBJECT-TYPE
			SYNTAX Integer32
			MAX-ACCESS read-only
			STATUS current
			DESCRIPTION
				"Description."
			::= { ntpPeerEntry 8 }

		
--             1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1402.3.1.9
-- 1.3.6.1.4.1.3807.2.1406.3.1.9
		-- 1.3.6.1.4.1.3807.2.1406.3.1.9
		ntpPeerEntryStatus OBJECT-TYPE
			SYNTAX Integer32
			MAX-ACCESS read-write
			STATUS current
			DESCRIPTION
				"Description."
			::= { ntpPeerEntry 9 }

		
--             1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1402.3.1.10
-- 1.3.6.1.4.1.3807.2.1406.3.1.10
		-- 1.3.6.1.4.1.3807.2.1406.3.1.10
		ntpPeerAssociationState OBJECT-TYPE
			SYNTAX Integer32
			MAX-ACCESS read-only
			STATUS current
			DESCRIPTION
				"Description."
			::= { ntpPeerEntry 10 }

		
--             1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1402.3.1.11
-- 1.3.6.1.4.1.3807.2.1406.3.1.11
		-- 1.3.6.1.4.1.3807.2.1406.3.1.11
		ntpPeerMulticastTtl OBJECT-TYPE
			SYNTAX Unsigned32
			MAX-ACCESS read-write
			STATUS current
			DESCRIPTION
				"Description."
			::= { ntpPeerEntry 11 }

		
--             1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1402.3.1.12
-- 1.3.6.1.4.1.3807.2.1406.3.1.12
		-- 1.3.6.1.4.1.3807.2.1406.3.1.12
		ntpPeerMulticastAddr OBJECT-TYPE
			SYNTAX InetAddress
			MAX-ACCESS read-write
			STATUS current
			DESCRIPTION
				"Description."
			::= { ntpPeerEntry 12 }

		
--             1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1402.3.1.13
-- 1.3.6.1.4.1.3807.2.1406.3.1.13
		-- 1.3.6.1.4.1.3807.2.1406.3.1.13
		ntpPeerStratum OBJECT-TYPE
			SYNTAX INTEGER
			MAX-ACCESS read-only
			STATUS current
			DESCRIPTION
				"Description."
			::= { ntpPeerEntry 13 }

		
--         1.3.6.1.4.1.3807.2.1402.3.1.14
-- 1.3.6.1.4.1.3807.2.1402.3.1.14
-- 1.3.6.1.4.1.3807.2.1402.3.1.14
-- 1.3.6.1.4.1.3807.2.1402.3.1.14
-- 1.3.6.1.4.1.3807.2.1402.3.1.14
-- 1.3.6.1.4.1.3807.2.1402.3.1.14
-- 1.3.6.1.4.1.3807.2.1402.3.1.14
-- 1.3.6.1.4.1.3807.2.1406.3.1.14
		-- 1.3.6.1.4.1.3807.2.1406.3.1.14
		ntpPeerOffset OBJECT-TYPE
			SYNTAX OCTET STRING
			MAX-ACCESS read-only
			STATUS current
			DESCRIPTION
				"Description."
			::= { ntpPeerEntry 14 }

		
--         1.3.6.1.4.1.3807.2.1402.3.1.15
-- 1.3.6.1.4.1.3807.2.1402.3.1.15
-- 1.3.6.1.4.1.3807.2.1402.3.1.15
-- 1.3.6.1.4.1.3807.2.1402.3.1.15
-- 1.3.6.1.4.1.3807.2.1402.3.1.15
-- 1.3.6.1.4.1.3807.2.1402.3.1.15
-- 1.3.6.1.4.1.3807.2.1402.3.1.15
-- 1.3.6.1.4.1.3807.2.1406.3.1.15
		-- 1.3.6.1.4.1.3807.2.1406.3.1.15
		ntpPeerDelay OBJECT-TYPE
			SYNTAX OCTET STRING
			MAX-ACCESS read-only
			STATUS current
			DESCRIPTION
				"Description."
			::= { ntpPeerEntry 15 }

		
--         1.3.6.1.4.1.3807.2.1402.3.1.16
-- 1.3.6.1.4.1.3807.2.1402.3.1.16
-- 1.3.6.1.4.1.3807.2.1402.3.1.16
-- 1.3.6.1.4.1.3807.2.1402.3.1.16
-- 1.3.6.1.4.1.3807.2.1402.3.1.16
-- 1.3.6.1.4.1.3807.2.1402.3.1.16
-- 1.3.6.1.4.1.3807.2.1402.3.1.16
-- 1.3.6.1.4.1.3807.2.1406.3.1.16
		-- 1.3.6.1.4.1.3807.2.1406.3.1.16
		ntpPeerDispersion OBJECT-TYPE
			SYNTAX OCTET STRING
			MAX-ACCESS read-only
			STATUS current
			DESCRIPTION
				"Description."
			::= { ntpPeerEntry 16 }

		
--   1.3.6.1.4.1.3807.2.1402.3.1.17
-- 1.3.6.1.4.1.3807.2.1406.3.1.17
		-- 1.3.6.1.4.1.3807.2.1406.3.1.17
		ntpPeerVrid OBJECT-TYPE
			SYNTAX INTEGER
			MAX-ACCESS read-write
			STATUS current
			DESCRIPTION
				"Description."
			::= { ntpPeerEntry 17 }
			
		-- 1.3.6.1.4.1.3807.2.1406.3.1.18
		ntpPeerSourceInterface OBJECT-TYPE
			SYNTAX INTEGER
			MAX-ACCESS read-write
			STATUS current
			DESCRIPTION
				"Description."
			::= { ntpPeerEntry 18 }

		
--             1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1402.4
-- 1.3.6.1.4.1.3807.2.1406.4
		-- 1.3.6.1.4.1.3807.2.1406.4
		ntpAssociationPeerTable OBJECT-TYPE
			SYNTAX SEQUENCE OF NtpAssociationPeerEntry
			MAX-ACCESS not-accessible
			STATUS current
			DESCRIPTION
				"Description."
			::= { ntp 4 }

		
--             1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1402.4.1
-- 1.3.6.1.4.1.3807.2.1406.4.1
		-- 1.3.6.1.4.1.3807.2.1406.4.1
		ntpAssociationPeerEntry OBJECT-TYPE
			SYNTAX NtpAssociationPeerEntry
			MAX-ACCESS not-accessible
			STATUS current
			DESCRIPTION
				"Description."
			INDEX { ntpAssociationPeerId }
			::= { ntpAssociationPeerTable 1 }

		
		NtpAssociationPeerEntry ::=
			SEQUENCE { 
				ntpAssociationPeerId
					Integer32,
				ntpAssociationPeerWorkMode
					Integer32,
				ntpAssociationPeerAddrType
					Integer32,
				ntpAssociationPeerHostAddr
					InetAddress,
				ntpAssociationPeerPeerAddr
					InetAddress,
				ntpAssociationPeerVersion
					Integer32,
				ntpAssociationPeerKeyId
					Unsigned32,
				ntpAssociationPeerPort
					Integer32,
				ntpAssociationPeerEntryStatus
					Integer32,
				ntpAssociationPeerReferenceClock
					InetAddress,
				ntpAssociationPeerClockState
					INTEGER,
				ntpAssociationPeerClockOffset
					OCTET STRING,
				ntpAssociationPeerClockDelay
					OCTET STRING,
				ntpAssociationPeerPrecison
					INTEGER,
				ntpAssociationPeerReferTime
					Counter64,
				ntpAssociationPeerOrgTime
					Counter64,
				ntpAssociationPeerRcvTime
					Counter64,
				ntpAssociationPeerXmtTime
					Counter64,
				ntpAssociationPeerRootDelay
					OCTET STRING,
				ntpAssociationPeerPeerWorkMode
					INTEGER,
				ntpAssociationPeerSourceAddr
					InetAddress,
				ntpAssociationPeerStratum
					INTEGER,
				ntpAssociationPeerLocalPoll
					INTEGER,
				ntpAssociationPeerPeerPoll
					INTEGER,
				ntpAssociationPeerClockDisper
					OCTET STRING,
				ntpAssociationPeerRootDisper
					OCTET STRING,
				ntpAssociationPeerMulticastTtl
					Unsigned32,
				ntpAssociationPeerMulticastAddr
					InetAddress,
				ntpAssociationPeerFilterTime
					Counter64,
				ntpAssociationPeerFilterDelay
					OCTET STRING,
				ntpAssociationPeerFilterOffset
					OCTET STRING,
				ntpAssociationPeerFilterDispersion
					OCTET STRING
			 }

--             1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1402.4.1.1
-- 1.3.6.1.4.1.3807.2.1406.4.1.1
		-- 1.3.6.1.4.1.3807.2.1406.4.1.1
		ntpAssociationPeerId OBJECT-TYPE
			SYNTAX Integer32
			MAX-ACCESS read-only
			STATUS current
			DESCRIPTION
				"Description."
			::= { ntpAssociationPeerEntry 1 }

		
--             1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1402.4.1.2
-- 1.3.6.1.4.1.3807.2.1406.4.1.2
		-- 1.3.6.1.4.1.3807.2.1406.4.1.2
		ntpAssociationPeerWorkMode OBJECT-TYPE
			SYNTAX Integer32
			MAX-ACCESS read-only
			STATUS current
			DESCRIPTION
				"Description."
			::= { ntpAssociationPeerEntry 2 }

		
--             1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1402.4.1.3
-- 1.3.6.1.4.1.3807.2.1406.4.1.3
		-- 1.3.6.1.4.1.3807.2.1406.4.1.3
		ntpAssociationPeerAddrType OBJECT-TYPE
			SYNTAX Integer32
			MAX-ACCESS read-only
			STATUS current
			DESCRIPTION
				"Description."
			::= { ntpAssociationPeerEntry 3 }

		
--             1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1402.4.1.4
-- 1.3.6.1.4.1.3807.2.1406.4.1.4
		-- 1.3.6.1.4.1.3807.2.1406.4.1.4
		ntpAssociationPeerHostAddr OBJECT-TYPE
			SYNTAX InetAddress
			MAX-ACCESS read-only
			STATUS current
			DESCRIPTION
				"Description."
			::= { ntpAssociationPeerEntry 4 }

		
--             1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1402.4.1.5
-- 1.3.6.1.4.1.3807.2.1406.4.1.5
		-- 1.3.6.1.4.1.3807.2.1406.4.1.5
		ntpAssociationPeerPeerAddr OBJECT-TYPE
			SYNTAX InetAddress
			MAX-ACCESS read-only
			STATUS current
			DESCRIPTION
				"Description."
			::= { ntpAssociationPeerEntry 5 }

		
--             1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1402.4.1.6
-- 1.3.6.1.4.1.3807.2.1406.4.1.6
		-- 1.3.6.1.4.1.3807.2.1406.4.1.6
		ntpAssociationPeerVersion OBJECT-TYPE
			SYNTAX Integer32
			MAX-ACCESS read-only
			STATUS current
			DESCRIPTION
				"Description."
			::= { ntpAssociationPeerEntry 6 }

		
--             1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1402.4.1.7
-- 1.3.6.1.4.1.3807.2.1406.4.1.7
		-- 1.3.6.1.4.1.3807.2.1406.4.1.7
		ntpAssociationPeerKeyId OBJECT-TYPE
			SYNTAX Unsigned32
			MAX-ACCESS read-only
			STATUS current
			DESCRIPTION
				"Description."
			::= { ntpAssociationPeerEntry 7 }

		
--             1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1402.4.1.8
-- 1.3.6.1.4.1.3807.2.1406.4.1.8
		-- 1.3.6.1.4.1.3807.2.1406.4.1.8
		ntpAssociationPeerPort OBJECT-TYPE
			SYNTAX Integer32
			MAX-ACCESS read-only
			STATUS current
			DESCRIPTION
				"Description."
			::= { ntpAssociationPeerEntry 8 }

		
--             1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1402.4.1.9
-- 1.3.6.1.4.1.3807.2.1406.4.1.9
		-- 1.3.6.1.4.1.3807.2.1406.4.1.9
		ntpAssociationPeerEntryStatus OBJECT-TYPE
			SYNTAX Integer32
			MAX-ACCESS read-only
			STATUS current
			DESCRIPTION
				"Description."
			::= { ntpAssociationPeerEntry 9 }

		
--             1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1402.4.1.10
-- 1.3.6.1.4.1.3807.2.1406.4.1.10
		-- 1.3.6.1.4.1.3807.2.1406.4.1.10
		ntpAssociationPeerReferenceClock OBJECT-TYPE
			SYNTAX InetAddress
			MAX-ACCESS read-only
			STATUS current
			DESCRIPTION
				"Description."
			::= { ntpAssociationPeerEntry 10 }

		
--             1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1402.4.1.11
-- 1.3.6.1.4.1.3807.2.1406.4.1.11
		-- 1.3.6.1.4.1.3807.2.1406.4.1.11
		ntpAssociationPeerClockState OBJECT-TYPE
			SYNTAX INTEGER
			MAX-ACCESS read-only
			STATUS current
			DESCRIPTION
				"Description."
			::= { ntpAssociationPeerEntry 11 }

		
--             1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1402.4.1.12
-- 1.3.6.1.4.1.3807.2.1406.4.1.12
		-- 1.3.6.1.4.1.3807.2.1406.4.1.12
		ntpAssociationPeerClockOffset OBJECT-TYPE
			SYNTAX OCTET STRING
			MAX-ACCESS read-only
			STATUS current
			DESCRIPTION
				"Description."
			::= { ntpAssociationPeerEntry 12 }

		
--             1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1402.4.1.13
-- 1.3.6.1.4.1.3807.2.1406.4.1.13
		-- 1.3.6.1.4.1.3807.2.1406.4.1.13
		ntpAssociationPeerClockDelay OBJECT-TYPE
			SYNTAX OCTET STRING
			MAX-ACCESS read-only
			STATUS current
			DESCRIPTION
				"Description."
			::= { ntpAssociationPeerEntry 13 }

		
--             1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1402.4.1.14
-- 1.3.6.1.4.1.3807.2.1406.4.1.14
		-- 1.3.6.1.4.1.3807.2.1406.4.1.14
		ntpAssociationPeerPrecison OBJECT-TYPE
			SYNTAX INTEGER
			MAX-ACCESS read-only
			STATUS current
			DESCRIPTION
				"Description."
			::= { ntpAssociationPeerEntry 14 }

		
--             1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1402.4.1.15
-- 1.3.6.1.4.1.3807.2.1406.4.1.15
		-- 1.3.6.1.4.1.3807.2.1406.4.1.15
		ntpAssociationPeerReferTime OBJECT-TYPE
			SYNTAX Counter64
			MAX-ACCESS read-only
			STATUS current
			DESCRIPTION
				"Description."
			::= { ntpAssociationPeerEntry 15 }

		
--             1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1402.4.1.16
-- 1.3.6.1.4.1.3807.2.1406.4.1.16
		-- 1.3.6.1.4.1.3807.2.1406.4.1.16
		ntpAssociationPeerOrgTime OBJECT-TYPE
			SYNTAX Counter64
			MAX-ACCESS read-only
			STATUS current
			DESCRIPTION
				"Description."
			::= { ntpAssociationPeerEntry 16 }

		
--             1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1402.4.1.17
-- 1.3.6.1.4.1.3807.2.1406.4.1.17
		-- 1.3.6.1.4.1.3807.2.1406.4.1.17
		ntpAssociationPeerRcvTime OBJECT-TYPE
			SYNTAX Counter64
			MAX-ACCESS read-only
			STATUS current
			DESCRIPTION
				"Description."
			::= { ntpAssociationPeerEntry 17 }

		
--             1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1402.4.1.18
-- 1.3.6.1.4.1.3807.2.1406.4.1.18
		-- 1.3.6.1.4.1.3807.2.1406.4.1.18
		ntpAssociationPeerXmtTime OBJECT-TYPE
			SYNTAX Counter64
			MAX-ACCESS read-only
			STATUS current
			DESCRIPTION
				"Description."
			::= { ntpAssociationPeerEntry 18 }

		
--             1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1402.4.1.19
-- 1.3.6.1.4.1.3807.2.1406.4.1.19
		-- 1.3.6.1.4.1.3807.2.1406.4.1.19
		ntpAssociationPeerRootDelay OBJECT-TYPE
			SYNTAX OCTET STRING
			MAX-ACCESS read-only
			STATUS current
			DESCRIPTION
				"Description."
			::= { ntpAssociationPeerEntry 19 }

		
--             1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1402.4.1.20
-- 1.3.6.1.4.1.3807.2.1406.4.1.20
		-- 1.3.6.1.4.1.3807.2.1406.4.1.20
		ntpAssociationPeerPeerWorkMode OBJECT-TYPE
			SYNTAX INTEGER
			MAX-ACCESS read-only
			STATUS current
			DESCRIPTION
				"Description."
			::= { ntpAssociationPeerEntry 20 }

		
--             1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1402.4.1.21
-- 1.3.6.1.4.1.3807.2.1406.4.1.21
		-- 1.3.6.1.4.1.3807.2.1406.4.1.21
		ntpAssociationPeerSourceAddr OBJECT-TYPE
			SYNTAX InetAddress
			MAX-ACCESS read-only
			STATUS current
			DESCRIPTION
				"Description."
			::= { ntpAssociationPeerEntry 21 }

		
--             1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1402.4.1.22
-- 1.3.6.1.4.1.3807.2.1406.4.1.22
		-- 1.3.6.1.4.1.3807.2.1406.4.1.22
		ntpAssociationPeerStratum OBJECT-TYPE
			SYNTAX INTEGER
			MAX-ACCESS read-only
			STATUS current
			DESCRIPTION
				"Description."
			::= { ntpAssociationPeerEntry 22 }

		
--             1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1402.4.1.23
-- 1.3.6.1.4.1.3807.2.1406.4.1.23
		-- 1.3.6.1.4.1.3807.2.1406.4.1.23
		ntpAssociationPeerLocalPoll OBJECT-TYPE
			SYNTAX INTEGER
			MAX-ACCESS read-only
			STATUS current
			DESCRIPTION
				"Description."
			::= { ntpAssociationPeerEntry 23 }

		
--             1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1402.4.1.24
-- 1.3.6.1.4.1.3807.2.1406.4.1.24
		-- 1.3.6.1.4.1.3807.2.1406.4.1.24
		ntpAssociationPeerPeerPoll OBJECT-TYPE
			SYNTAX INTEGER
			MAX-ACCESS read-only
			STATUS current
			DESCRIPTION
				"Description."
			::= { ntpAssociationPeerEntry 24 }

		
--             1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1402.4.1.25
-- 1.3.6.1.4.1.3807.2.1406.4.1.25
		-- 1.3.6.1.4.1.3807.2.1406.4.1.25
		ntpAssociationPeerClockDisper OBJECT-TYPE
			SYNTAX OCTET STRING
			MAX-ACCESS read-only
			STATUS current
			DESCRIPTION
				"Description."
			::= { ntpAssociationPeerEntry 25 }

		
--             1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1402.4.1.26
-- 1.3.6.1.4.1.3807.2.1406.4.1.26
		-- 1.3.6.1.4.1.3807.2.1406.4.1.26
		ntpAssociationPeerRootDisper OBJECT-TYPE
			SYNTAX OCTET STRING
			MAX-ACCESS read-only
			STATUS current
			DESCRIPTION
				"Description."
			::= { ntpAssociationPeerEntry 26 }

		
--            1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1402.4.1.27
-- 1.3.6.1.4.1.3807.2.1406.4.1.27
		-- 1.3.6.1.4.1.3807.2.1406.4.1.27
		ntpAssociationPeerMulticastTtl OBJECT-TYPE
			SYNTAX Unsigned32
			MAX-ACCESS read-only
			STATUS current
			DESCRIPTION
				"Description."
			::= { ntpAssociationPeerEntry 27 }

		
--            1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1402.4.1.28
-- 1.3.6.1.4.1.3807.2.1406.4.1.28
		-- 1.3.6.1.4.1.3807.2.1406.4.1.28
		ntpAssociationPeerMulticastAddr OBJECT-TYPE
			SYNTAX InetAddress
			MAX-ACCESS read-only
			STATUS current
			DESCRIPTION
				"Description."
			::= { ntpAssociationPeerEntry 28 }

		
--          1.3.6.1.4.1.3807.2.1402.4.1.29
-- 1.3.6.1.4.1.3807.2.1402.4.1.29
-- 1.3.6.1.4.1.3807.2.1402.4.1.29
-- 1.3.6.1.4.1.3807.2.1402.4.1.29
-- 1.3.6.1.4.1.3807.2.1402.4.1.29
-- 1.3.6.1.4.1.3807.2.1402.4.1.29
-- 1.3.6.1.4.1.3807.2.1402.4.1.29
-- 1.3.6.1.4.1.3807.2.1402.4.1.29
-- 1.3.6.1.4.1.3807.2.1406.4.1.29
		-- 1.3.6.1.4.1.3807.2.1406.4.1.29
		ntpAssociationPeerFilterTime OBJECT-TYPE
			SYNTAX Counter64
			MAX-ACCESS read-only
			STATUS current
			DESCRIPTION
				"Description."
			::= { ntpAssociationPeerEntry 29 }

		
--          1.3.6.1.4.1.3807.2.1402.4.1.30
-- 1.3.6.1.4.1.3807.2.1402.4.1.30
-- 1.3.6.1.4.1.3807.2.1402.4.1.30
-- 1.3.6.1.4.1.3807.2.1402.4.1.30
-- 1.3.6.1.4.1.3807.2.1402.4.1.30
-- 1.3.6.1.4.1.3807.2.1402.4.1.30
-- 1.3.6.1.4.1.3807.2.1402.4.1.30
-- 1.3.6.1.4.1.3807.2.1402.4.1.30
-- 1.3.6.1.4.1.3807.2.1406.4.1.30
		-- 1.3.6.1.4.1.3807.2.1406.4.1.30
		ntpAssociationPeerFilterDelay OBJECT-TYPE
			SYNTAX OCTET STRING
			MAX-ACCESS read-only
			STATUS current
			DESCRIPTION
				"Description."
			::= { ntpAssociationPeerEntry 30 }

		
--          1.3.6.1.4.1.3807.2.1402.4.1.31
-- 1.3.6.1.4.1.3807.2.1402.4.1.31
-- 1.3.6.1.4.1.3807.2.1402.4.1.31
-- 1.3.6.1.4.1.3807.2.1402.4.1.31
-- 1.3.6.1.4.1.3807.2.1402.4.1.31
-- 1.3.6.1.4.1.3807.2.1402.4.1.31
-- 1.3.6.1.4.1.3807.2.1402.4.1.31
-- 1.3.6.1.4.1.3807.2.1402.4.1.31
-- 1.3.6.1.4.1.3807.2.1406.4.1.31
		-- 1.3.6.1.4.1.3807.2.1406.4.1.31
		ntpAssociationPeerFilterOffset OBJECT-TYPE
			SYNTAX OCTET STRING
			MAX-ACCESS read-only
			STATUS current
			DESCRIPTION
				"Description."
			::= { ntpAssociationPeerEntry 31 }

		
--          1.3.6.1.4.1.3807.2.1402.4.1.32
-- 1.3.6.1.4.1.3807.2.1402.4.1.32
-- 1.3.6.1.4.1.3807.2.1402.4.1.32
-- 1.3.6.1.4.1.3807.2.1402.4.1.32
-- 1.3.6.1.4.1.3807.2.1402.4.1.32
-- 1.3.6.1.4.1.3807.2.1402.4.1.32
-- 1.3.6.1.4.1.3807.2.1402.4.1.32
-- 1.3.6.1.4.1.3807.2.1402.4.1.32
-- 1.3.6.1.4.1.3807.2.1406.4.1.32
		-- 1.3.6.1.4.1.3807.2.1406.4.1.32
		ntpAssociationPeerFilterDispersion OBJECT-TYPE
			SYNTAX OCTET STRING
			MAX-ACCESS read-only
			STATUS current
			DESCRIPTION
				"Description."
			::= { ntpAssociationPeerEntry 32 }

		
	
	END

--
-- ntp.mib
--
