--
-- ND-SNOOPING-MIB.mib
-- MIB generated by MG-SOFT Visual MIB Builder Version 4.0 Build 349
-- Friday, June 27, 2014 at 15:41:57
--

	ND-SNOOPING-MIB DEFINITIONS ::= BEGIN
 
		IMPORTS
			InetAddress			
				FROM INET-ADDRESS-MIB			
			Integer32, Unsigned32, Counter32, OBJECT-TYPE			
				FROM SNMPv2-SMI			
			MacAddress, TEXTUAL-CONVENTION			
				FROM SNMPv2-TC			
			qtechProtocol			
				FROM QTECH-SMI;
	
	
--
-- Textual conventions
--
	
		EntryStatus ::= TEXTUAL-CONVENTION
			STATUS current
			DESCRIPTION 
				"entry status."
			SYNTAX INTEGER
				{
				valid(1),
				createRequest(2),
				underCreation(3),
				invalid(4)
				}

	
--
-- Node definitions
--
	
		-- 1.3.6.1.4.1.3807.2.1408
		ndSnooping OBJECT IDENTIFIER ::= { qtechProtocol 1408 }

		
		-- 1.3.6.1.4.1.3807.2.1408.1
		ndSnoopingGlobalConfig OBJECT IDENTIFIER ::= { ndSnooping 1 }

		
		-- 1.3.6.1.4.1.3807.2.1408.1.1
		ndSnoopingGlobalEnable OBJECT-TYPE
			SYNTAX INTEGER
				{
				enable(1),
				disable(2)
				}
			MAX-ACCESS read-write
			STATUS current
			DESCRIPTION
				"Description."
			::= { ndSnoopingGlobalConfig 1 }

		
		-- 1.3.6.1.4.1.3807.2.1408.1.2
		ndSnoopingGlobalAgingEnable OBJECT-TYPE
			SYNTAX INTEGER
				{
				enabel(1),
				disable(2)
				}
			MAX-ACCESS read-write
			STATUS current
			DESCRIPTION
				"Description."
			::= { ndSnoopingGlobalConfig 2 }

		
		-- 1.3.6.1.4.1.3807.2.1408.1.3
		ndSnoopingGlobalNudCount OBJECT-TYPE
			SYNTAX Unsigned32
			MAX-ACCESS read-write
			STATUS current
			DESCRIPTION
				"Description."
			::= { ndSnoopingGlobalConfig 3 }

		
		-- 1.3.6.1.4.1.3807.2.1408.1.4
		ndSnoopingGlobalDetectTime OBJECT-TYPE
			SYNTAX Unsigned32
			MAX-ACCESS read-write
			STATUS current
			DESCRIPTION
				"Description."
			::= { ndSnoopingGlobalConfig 4 }

		
		-- 1.3.6.1.4.1.3807.2.1408.1.5
		ndSnoopingGlobalFlushUser OBJECT-TYPE
			SYNTAX Integer32
			MAX-ACCESS read-write
			STATUS current
			DESCRIPTION
				"Description."
			::= { ndSnoopingGlobalConfig 5 }

		
		-- 1.3.6.1.4.1.3807.2.1408.1.6
		ndSnoopingGlobalFlushPrefix OBJECT-TYPE
			SYNTAX Integer32
			MAX-ACCESS read-write
			STATUS current
			DESCRIPTION
				"Description."
			::= { ndSnoopingGlobalConfig 6 }

		
		-- 1.3.6.1.4.1.3807.2.1408.1.7
		ndSnoopingGlobalMaxUserNum OBJECT-TYPE
			SYNTAX Unsigned32
			MAX-ACCESS read-only
			STATUS current
			DESCRIPTION
				"Description."
			::= { ndSnoopingGlobalConfig 7 }

		
		-- 1.3.6.1.4.1.3807.2.1408.1.8
		ndSnoopingGlobalCurUserNum OBJECT-TYPE
			SYNTAX Unsigned32
			MAX-ACCESS read-only
			STATUS current
			DESCRIPTION
				"Description."
			::= { ndSnoopingGlobalConfig 8 }

		
		-- 1.3.6.1.4.1.3807.2.1408.1.9
		ndSnoopingGlobalMaxIfNum OBJECT-TYPE
			SYNTAX Unsigned32
			MAX-ACCESS read-only
			STATUS current
			DESCRIPTION
				"Description."
			::= { ndSnoopingGlobalConfig 9 }

		
		-- 1.3.6.1.4.1.3807.2.1408.1.10
		ndSnoopingGlobalCurIfNum OBJECT-TYPE
			SYNTAX Unsigned32
			MAX-ACCESS read-only
			STATUS current
			DESCRIPTION
				"Description."
			::= { ndSnoopingGlobalConfig 10 }

		
		-- 1.3.6.1.4.1.3807.2.1408.1.11
		ndSnoopingGlobalMaxPrefixNum OBJECT-TYPE
			SYNTAX Unsigned32
			MAX-ACCESS read-only
			STATUS current
			DESCRIPTION
				"Description."
			::= { ndSnoopingGlobalConfig 11 }

		
		-- 1.3.6.1.4.1.3807.2.1408.1.12
		ndSnoopingGlobalCurPrefixNum OBJECT-TYPE
			SYNTAX Unsigned32
			MAX-ACCESS read-only
			STATUS current
			DESCRIPTION
				"Description."
			::= { ndSnoopingGlobalConfig 12 }

		
		-- 1.3.6.1.4.1.3807.2.1408.2
		ndSnoopingInterfaceTable OBJECT-TYPE
			SYNTAX SEQUENCE OF NdSnoopingInterfaceEntry
			MAX-ACCESS not-accessible
			STATUS current
			DESCRIPTION
				"Description."
			::= { ndSnooping 2 }

		
		-- 1.3.6.1.4.1.3807.2.1408.2.1
		ndSnoopingInterfaceEntry OBJECT-TYPE
			SYNTAX NdSnoopingInterfaceEntry
			MAX-ACCESS not-accessible
			STATUS current
			DESCRIPTION
				"Description."
			INDEX { ndSnoopingInterfaceIfunit }
			::= { ndSnoopingInterfaceTable 1 }

		
		NdSnoopingInterfaceEntry ::=
			SEQUENCE { 
				ndSnoopingInterfaceIfunit
					Integer32,
				ndSnoopingInterfaceTrust
					INTEGER,
				ndSnoopingInterfaceMaxUserNum
					Unsigned32,
				ndSnoopingInterfaceCurUserNum
					Unsigned32,
				ndSnoopingInterfaceEnable
					INTEGER
			 }

		-- 1.3.6.1.4.1.3807.2.1408.2.1.1
		ndSnoopingInterfaceIfunit OBJECT-TYPE
			SYNTAX Integer32
			MAX-ACCESS read-only
			STATUS current
			DESCRIPTION
				"Description."
			::= { ndSnoopingInterfaceEntry 1 }

		
		-- 1.3.6.1.4.1.3807.2.1408.2.1.2
		ndSnoopingInterfaceTrust OBJECT-TYPE
			SYNTAX INTEGER
				{
				untrust(0),
				trust(1)
				}
			MAX-ACCESS read-write
			STATUS current
			DESCRIPTION
				"Description."
			::= { ndSnoopingInterfaceEntry 2 }

		
		-- 1.3.6.1.4.1.3807.2.1408.2.1.3
		ndSnoopingInterfaceMaxUserNum OBJECT-TYPE
			SYNTAX Unsigned32
			MAX-ACCESS read-write
			STATUS current
			DESCRIPTION
				"Description."
			::= { ndSnoopingInterfaceEntry 3 }

		
		-- 1.3.6.1.4.1.3807.2.1408.2.1.4
		ndSnoopingInterfaceCurUserNum OBJECT-TYPE
			SYNTAX Unsigned32
			MAX-ACCESS read-only
			STATUS current
			DESCRIPTION
				"Description."
			::= { ndSnoopingInterfaceEntry 4 }

		
		-- 1.3.6.1.4.1.3807.2.1408.2.1.5
		ndSnoopingInterfaceEnable OBJECT-TYPE
			SYNTAX INTEGER
				{
				enable(1),
				disable(2)
				}
			MAX-ACCESS read-write
			STATUS current
			DESCRIPTION
				"Description."
			::= { ndSnoopingInterfaceEntry 5 }

		
		-- 1.3.6.1.4.1.3807.2.1408.3
		ndSnoopingUserTable OBJECT-TYPE
			SYNTAX SEQUENCE OF NdSnoopingUserEntry
			MAX-ACCESS not-accessible
			STATUS current
			DESCRIPTION
				"Description."
			::= { ndSnooping 3 }

		
		-- 1.3.6.1.4.1.3807.2.1408.3.1
		ndSnoopingUserEntry OBJECT-TYPE
			SYNTAX NdSnoopingUserEntry
			MAX-ACCESS not-accessible
			STATUS current
			DESCRIPTION
				"Description."
			INDEX { ndSnoopingUserIp, ndSnoopingUserVrfId }
			::= { ndSnoopingUserTable 1 }

		
		NdSnoopingUserEntry ::=
			SEQUENCE { 
				ndSnoopingUserIp
					InetAddress,
				ndSnoopingUserVrfId
					Unsigned32,
				ndSnoopingUserIfIndex
					Unsigned32,
				ndSnoopingUserMac
					MacAddress,
				ndSnoopingUserUpdateTime
					Unsigned32,
				ndSnoopingUserLifeTime
					Unsigned32,
				ndSnoopingUserNudCount
					Counter32,
				ndSnoopingUserType
					INTEGER,
				ndSnoopingUserEntryStatus
					EntryStatus
			 }

		-- 1.3.6.1.4.1.3807.2.1408.3.1.1
		ndSnoopingUserIp OBJECT-TYPE
			SYNTAX InetAddress
			MAX-ACCESS read-only
			STATUS current
			DESCRIPTION
				"Description."
			::= { ndSnoopingUserEntry 1 }

		
		-- 1.3.6.1.4.1.3807.2.1408.3.1.2
		ndSnoopingUserVrfId OBJECT-TYPE
			SYNTAX Unsigned32
			MAX-ACCESS read-only
			STATUS current
			DESCRIPTION
				"Description."
			::= { ndSnoopingUserEntry 2 }

		
		-- 1.3.6.1.4.1.3807.2.1408.3.1.3
		ndSnoopingUserIfIndex OBJECT-TYPE
			SYNTAX Unsigned32
			MAX-ACCESS read-write
			STATUS current
			DESCRIPTION
				"Description."
			::= { ndSnoopingUserEntry 3 }

		
		-- 1.3.6.1.4.1.3807.2.1408.3.1.4
		ndSnoopingUserMac OBJECT-TYPE
			SYNTAX MacAddress
			MAX-ACCESS read-write
			STATUS current
			DESCRIPTION
				"Description."
			::= { ndSnoopingUserEntry 4 }

		
		-- 1.3.6.1.4.1.3807.2.1408.3.1.5
		ndSnoopingUserUpdateTime OBJECT-TYPE
			SYNTAX Unsigned32
			MAX-ACCESS read-only
			STATUS current
			DESCRIPTION
				"Description."
			::= { ndSnoopingUserEntry 5 }

		
		-- 1.3.6.1.4.1.3807.2.1408.3.1.6
		ndSnoopingUserLifeTime OBJECT-TYPE
			SYNTAX Unsigned32
			MAX-ACCESS read-only
			STATUS current
			DESCRIPTION
				"Description."
			::= { ndSnoopingUserEntry 6 }

		
		-- 1.3.6.1.4.1.3807.2.1408.3.1.7
		ndSnoopingUserNudCount OBJECT-TYPE
			SYNTAX Counter32
			MAX-ACCESS read-only
			STATUS current
			DESCRIPTION
				"Description."
			::= { ndSnoopingUserEntry 7 }

		
		-- 1.3.6.1.4.1.3807.2.1408.3.1.8
		ndSnoopingUserType OBJECT-TYPE
			SYNTAX INTEGER
				{
				temp(0),
				dynamic(1),
				static(2)
				}
			MAX-ACCESS read-only
			STATUS current
			DESCRIPTION
				"Description."
			::= { ndSnoopingUserEntry 8 }

		
		-- 1.3.6.1.4.1.3807.2.1408.3.1.9
		ndSnoopingUserEntryStatus OBJECT-TYPE
			SYNTAX EntryStatus
			MAX-ACCESS read-write
			STATUS current
			DESCRIPTION
				"Description."
			::= { ndSnoopingUserEntry 9 }

		
		-- 1.3.6.1.4.1.3807.2.1408.4
		ndSnoopingPrefixTable OBJECT-TYPE
			SYNTAX SEQUENCE OF NdSnoopingPrefixEntry
			MAX-ACCESS not-accessible
			STATUS current
			DESCRIPTION
				"Description."
			::= { ndSnooping 4 }

		
		-- 1.3.6.1.4.1.3807.2.1408.4.1
		ndSnoopingPrefixEntry OBJECT-TYPE
			SYNTAX NdSnoopingPrefixEntry
			MAX-ACCESS not-accessible
			STATUS current
			DESCRIPTION
				"Description."
			INDEX { ndSnoopingPrefix, ndSnoopingPrefixLen }
			::= { ndSnoopingPrefixTable 1 }

		
		NdSnoopingPrefixEntry ::=
			SEQUENCE { 
				ndSnoopingPrefix
					InetAddress,
				ndSnoopingPrefixLen
					Unsigned32,
				ndSnoopingPrefixValidTime
					Unsigned32,
				ndSnoopingPrefixPreferTime
					Unsigned32,
				ndSnoopingPrefixUpdateTime
					Unsigned32,
				ndSnoopingPrefixEntryStatus
					EntryStatus
			 }

		-- 1.3.6.1.4.1.3807.2.1408.4.1.1
		ndSnoopingPrefix OBJECT-TYPE
			SYNTAX InetAddress
			MAX-ACCESS read-only
			STATUS current
			DESCRIPTION
				"Description."
			::= { ndSnoopingPrefixEntry 1 }

		
		-- 1.3.6.1.4.1.3807.2.1408.4.1.2
		ndSnoopingPrefixLen OBJECT-TYPE
			SYNTAX Unsigned32
			MAX-ACCESS read-only
			STATUS current
			DESCRIPTION
				"Description."
			::= { ndSnoopingPrefixEntry 2 }

		
		-- 1.3.6.1.4.1.3807.2.1408.4.1.3
		ndSnoopingPrefixValidTime OBJECT-TYPE
			SYNTAX Unsigned32
			MAX-ACCESS read-only
			STATUS current
			DESCRIPTION
				"Description."
			::= { ndSnoopingPrefixEntry 3 }

		
		-- 1.3.6.1.4.1.3807.2.1408.4.1.4
		ndSnoopingPrefixPreferTime OBJECT-TYPE
			SYNTAX Unsigned32
			MAX-ACCESS read-only
			STATUS current
			DESCRIPTION
				"Description."
			::= { ndSnoopingPrefixEntry 4 }

		
		-- 1.3.6.1.4.1.3807.2.1408.4.1.5
		ndSnoopingPrefixUpdateTime OBJECT-TYPE
			SYNTAX Unsigned32
			MAX-ACCESS read-only
			STATUS current
			DESCRIPTION
				"Description."
			::= { ndSnoopingPrefixEntry 5 }

		
		-- 1.3.6.1.4.1.3807.2.1408.4.1.6
		ndSnoopingPrefixEntryStatus OBJECT-TYPE
			SYNTAX EntryStatus
			MAX-ACCESS read-write
			STATUS current
			DESCRIPTION
				"Description."
			::= { ndSnoopingPrefixEntry 6 }

		
	
	END

--
-- ND-SNOOPING-MIB.mib
--
