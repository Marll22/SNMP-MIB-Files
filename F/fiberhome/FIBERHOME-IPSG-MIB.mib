QTECH-IPSG-MIB DEFINITIONS ::= BEGIN
 
		IMPORTS
			Integer32, Counter64,OBJECT-TYPE, MODULE-IDENTITY,NOTIFICATION-TYPE			
				FROM SNMPv2-SMI	
			MacAddress, RowStatus, TEXTUAL-CONVENTION            
          FROM SNMPv2-TC		
			qtechProtocol			
				FROM QTECH-SMI	;
	
		
--  1.3.6.1.4.1.3807.2.903
-- August 18, 2010 at 14:27 GMT
		wriIPSG MODULE-IDENTITY 
			LAST-UPDATED "201008181427Z"		-- August 18, 2010 at 14:27 GMT
			ORGANIZATION 
				"Organization."
			CONTACT-INFO 
				"Contact-info."
			DESCRIPTION 
				"Description."
			::= { qtechProtocol 903 }


	EntryStatus ::= TEXTUAL-CONVENTION
		STATUS current
		DESCRIPTION
				"entry status."
		SYNTAX INTEGER 
			{
				valid(1),
				createRequest(2),
				underCreation(3),
				invalid(4)
			}	
	
--
-- Node definitions
--
	
--  Node definitions
-- 
-- 1.3.6.1.4.1.3807.2.903.1
		wriIPSGIfTable OBJECT-TYPE
			SYNTAX SEQUENCE OF WriIPSGIfEntry
			MAX-ACCESS not-accessible
			STATUS current
			DESCRIPTION
				"Description."
			::= { wriIPSG 1 }

		
--  1.3.6.1.4.1.3807.2.903.1.1
		wriIPSGIfEntry OBJECT-TYPE
			SYNTAX WriIPSGIfEntry
			MAX-ACCESS not-accessible
			STATUS current
			DESCRIPTION
				"Description."
			INDEX { wriIPSGIfIndex }
			::= { wriIPSGIfTable 1 }

		
		WriIPSGIfEntry ::=
			SEQUENCE { 
				wriIPSGIfIndex
					Integer32,
				wriIPSGIfStatus
					INTEGER,
				wriIPSGIfCheckItem    OCTET STRING,
				wriIPSGIfAlarmStatus  INTEGER,
				wriIPSGIfAlarmLimit   Integer32,
				wriIPSGIfIpPktDrop    Counter64,
				wriIPSGIfReset        INTEGER
			 }

--  1.3.6.1.4.1.3807.2.903.1.1.1
		wriIPSGIfIndex OBJECT-TYPE
			SYNTAX Integer32
			MAX-ACCESS read-only
			STATUS current
			DESCRIPTION
				"Description."
			::= { wriIPSGIfEntry 1 }

		
--  1.3.6.1.4.1.3807.2.903.1.1.2
		wriIPSGIfStatus OBJECT-TYPE
			SYNTAX INTEGER
				{
				disable(2),
				enable(1)
				}
			MAX-ACCESS read-write
			STATUS current
			DESCRIPTION
				"Description."
			::= { wriIPSGIfEntry 2 }
			
--  1.3.6.1.4.1.3807.2.903.1.1.3
		wriIPSGIfCheckItem OBJECT-TYPE
			SYNTAX OCTET STRING
			MAX-ACCESS read-write
			STATUS current
			DESCRIPTION
				"Description."
			::= { wriIPSGIfEntry 3 }
			
--  1.3.6.1.4.1.3807.2.903.1.1.4
		wriIPSGIfAlarmStatus OBJECT-TYPE
			SYNTAX INTEGER
				{
				disable(2),
				enable(1)
				}
			MAX-ACCESS read-write
			STATUS current
			DESCRIPTION
				"Description."
			::= { wriIPSGIfEntry 4 }
			
--  1.3.6.1.4.1.3807.2.903.1.1.5
		wriIPSGIfAlarmLimit OBJECT-TYPE
			SYNTAX Integer32
			MAX-ACCESS read-write
			STATUS current
			DESCRIPTION
				"Description."
			::= { wriIPSGIfEntry 5 }	
	
--  1.3.6.1.4.1.3807.2.903.1.1.6
		wriIPSGIfIpPktDrop OBJECT-TYPE
			SYNTAX Counter64
			MAX-ACCESS read-only
			STATUS current
			DESCRIPTION
				"Description."
			::= { wriIPSGIfEntry 6 }	
						
-- 1.3.6.1.4.1.3807.2.903.1.1.7
		wriIPSGIfReset OBJECT-TYPE
			SYNTAX INTEGER
			MAX-ACCESS read-write
			STATUS current
			DESCRIPTION
				"Description."
			::= { wriIPSGIfEntry 7 }			
		
		
--  1.3.6.1.4.1.3807.2.903.2
		wriIPSGUserTable OBJECT-TYPE
			SYNTAX SEQUENCE OF WriIPSGUserEntry
			MAX-ACCESS not-accessible
			STATUS current
			DESCRIPTION
				"Description."
			::= { wriIPSG 2 }

--  1.3.6.1.4.1.3807.2.903.2.1
		wriIPSGUserEntry OBJECT-TYPE
			SYNTAX WriIPSGUserEntry
			MAX-ACCESS not-accessible
			STATUS current
			DESCRIPTION
				"Description."
			INDEX { wriIPSGUserIpAddrType, wriIPSGUserIpAddr, wriIPSGUserMac,
			wriIPSGUserVlan,wriIPSGUserIfUnit}
			::= { wriIPSGUserTable 1 }

		
		WriIPSGUserEntry ::=
			SEQUENCE { 
				wriIPSGUserIpAddrType
					Integer32,
				wriIPSGUserIpAddr
					OCTET STRING,
				wriIPSGUserMac
					MacAddress,					
				wriIPSGUserVlan
					INTEGER,
				wriIPSGUserIfUnit
					Integer32,
					
				wriIPSGUserTime
					Integer32,
				wriIPSGUserType
					Integer32,
				wriIPSGUserHwFlag
					OCTET STRING,
				wriIPSGUserEntryStatus
					INTEGER,
				wriIPSGUserMacPrefix
					Integer32,
				wriIPSGUserLastVlan
					Integer32
			 }

--  1.3.6.1.4.1.3807.2.903.2.1.1
		wriIPSGUserIpAddrType OBJECT-TYPE
			SYNTAX Integer32
			MAX-ACCESS read-only
			STATUS current
			DESCRIPTION
				"Description."
			::= { wriIPSGUserEntry 1 }

		
--  1.3.6.1.4.1.3807.2.903.2.1.2
		wriIPSGUserIpAddr OBJECT-TYPE
			SYNTAX OCTET STRING (SIZE (0..16))
			MAX-ACCESS read-only
			STATUS current
			DESCRIPTION
				"Description."
			::= { wriIPSGUserEntry 2 }
			
--  1.3.6.1.4.1.3807.2.903.2.1.3
		wriIPSGUserMac OBJECT-TYPE
			SYNTAX MacAddress
			MAX-ACCESS read-only
			STATUS current
			DESCRIPTION
				"Description."
			::= { wriIPSGUserEntry 3 }
		
--  1.3.6.1.4.1.3807.2.903.2.1.4
		wriIPSGUserVlan OBJECT-TYPE
			SYNTAX INTEGER (0..4096)
			MAX-ACCESS read-only
			STATUS current
			DESCRIPTION
				"Description."
			::= { wriIPSGUserEntry 4 }
	
--  1.3.6.1.4.1.3807.2.903.2.1.5
		wriIPSGUserIfUnit OBJECT-TYPE
			SYNTAX Integer32
			MAX-ACCESS read-only
			STATUS current
			DESCRIPTION
				"Description."
			::= { wriIPSGUserEntry 5 }
		
--  1.3.6.1.4.1.3807.2.903.2.1.6
		wriIPSGUserTime OBJECT-TYPE
			SYNTAX Integer32
			MAX-ACCESS read-only
			STATUS current
			DESCRIPTION
				"Description."
			::= { wriIPSGUserEntry 6 }

		
--  1.3.6.1.4.1.3807.2.903.2.1.7
		wriIPSGUserType OBJECT-TYPE
			SYNTAX Integer32
			MAX-ACCESS read-only
			STATUS current
			DESCRIPTION
				"Description."
			::= { wriIPSGUserEntry 7 }

		
--  1.3.6.1.4.1.3807.2.903.2.1.8
		wriIPSGUserHwFlag OBJECT-TYPE
			SYNTAX OCTET STRING
			MAX-ACCESS read-only
			STATUS current
			DESCRIPTION
				"Description."
			::= { wriIPSGUserEntry 8 }

--  1.3.6.1.4.1.3807.2.903.2.1.9
		wriIPSGUserEntryStatus OBJECT-TYPE
			SYNTAX EntryStatus
			MAX-ACCESS read-write
			STATUS current
			DESCRIPTION
				"Description."
			::= { wriIPSGUserEntry 9 }
			
--  1.3.6.1.4.1.3807.2.903.2.1.10
		wriIPSGUserMacPrefix OBJECT-TYPE
			SYNTAX Integer32
			MAX-ACCESS read-write
			STATUS current
			DESCRIPTION
				"Description."
			::= { wriIPSGUserEntry 10 }
		
--  1.3.6.1.4.1.3807.2.903.2.1.11
		wriIPSGUserLastVlan OBJECT-TYPE
			SYNTAX Integer32
			MAX-ACCESS read-write
			STATUS current
			DESCRIPTION
				"Description."
			::= { wriIPSGUserEntry 11 }		
		
				
	
		wriIPSGCommon OBJECT IDENTIFIER ::= { wriIPSG 3 }

		
		wriIPSGGlobalUserNum OBJECT-TYPE
			SYNTAX Integer32
			MAX-ACCESS read-only
			STATUS current
			DESCRIPTION
				"Description."
			::= { wriIPSGCommon 1 }

		wriIPSGGlobalUserMaxNum OBJECT-TYPE
			SYNTAX Integer32
			MAX-ACCESS read-only
			STATUS current
			DESCRIPTION
				"Description."
			::= { wriIPSGCommon 2 }
			
		wriIPSGGlobalIfMaxNum OBJECT-TYPE
			SYNTAX Integer32
			MAX-ACCESS read-only
			STATUS current
			DESCRIPTION
				"Description."
			::= { wriIPSGCommon 3 }
			
	wriIPSGTraps   OBJECT IDENTIFIER ::= { wriIPSG 0 }

	wriIPSGIpPktOver NOTIFICATION-TYPE
             OBJECTS { wriIPSGIfIndex, wriIPSGIfIpPktDrop}
             STATUS  current
             DESCRIPTION
               ""
            ::= { wriIPSGTraps 1 }
	
	
	
	
	END
