-- MIB XYLO-MIB-SMI (v1)

XYLO-MIB-SMI DEFINITIONS ::= BEGIN
IMPORTS 	 
 	enterprises	FROM 	RFC1155-SMI	 
 	DisplayString	FROM 	RFC1213-MIB	 
 	OBJECT-TYPE	FROM 	RFC-1212	 
 	;	 	 	 
xylogics	OBJECT IDENTIFIER 	::= { enterprises 15  }	 
-- 1.3.6.1.4.1.15
-- iso(1). org(3). dod(6). internet(1). private(4). enterprises(1). xylogics(15)
prod	OBJECT IDENTIFIER 	::= { xylogics 1  }	 
-- 1.3.6.1.4.1.15.1
-- iso(1). org(3). dod(6). internet(1). private(4). enterprises(1). xylogics(15). prod(1)
prodoid	OBJECT IDENTIFIER 	::= { prod 3  }	 
-- 1.3.6.1.4.1.15.1.3
-- iso(1). org(3). dod(6). internet(1). private(4). enterprises(1). xylogics(15). prod(1). prodoid(3)
unknown	OBJECT IDENTIFIER 	::= { prodoid 1  }	 
-- 1.3.6.1.4.1.15.1.3.1
-- iso(1). org(3). dod(6). internet(1). private(4). enterprises(1). xylogics(15). prod(1). prodoid(3). unknown(1)
annexII	OBJECT IDENTIFIER 	::= { prodoid 2  }	 
-- 1.3.6.1.4.1.15.1.3.2
-- iso(1). org(3). dod(6). internet(1). private(4). enterprises(1). xylogics(15). prod(1). prodoid(3). annexII(2)
annex3	OBJECT IDENTIFIER 	::= { prodoid 3  }	 
-- 1.3.6.1.4.1.15.1.3.3
-- iso(1). org(3). dod(6). internet(1). private(4). enterprises(1). xylogics(15). prod(1). prodoid(3). annex3(3)
microanx	OBJECT IDENTIFIER 	::= { prodoid 4  }	 
-- 1.3.6.1.4.1.15.1.3.4
-- iso(1). org(3). dod(6). internet(1). private(4). enterprises(1). xylogics(15). prod(1). prodoid(3). microanx(4)
microels	OBJECT IDENTIFIER 	::= { prodoid 5  }	 
-- 1.3.6.1.4.1.15.1.3.5
-- iso(1). org(3). dod(6). internet(1). private(4). enterprises(1). xylogics(15). prod(1). prodoid(3). microels(5)
csmim1	OBJECT IDENTIFIER 	::= { prodoid 6  }	 
-- 1.3.6.1.4.1.15.1.3.6
-- iso(1). org(3). dod(6). internet(1). private(4). enterprises(1). xylogics(15). prod(1). prodoid(3). csmim1(6)
ods	OBJECT IDENTIFIER 	::= { prodoid 7  }	 
-- 1.3.6.1.4.1.15.1.3.7
-- iso(1). org(3). dod(6). internet(1). private(4). enterprises(1). xylogics(15). prod(1). prodoid(3). ods(7)
bay5390	OBJECT IDENTIFIER 	::= { prodoid 8  }	 
-- 1.3.6.1.4.1.15.1.3.8
-- iso(1). org(3). dod(6). internet(1). private(4). enterprises(1). xylogics(15). prod(1). prodoid(3). bay5390(8)
csmim2	OBJECT IDENTIFIER 	::= { prodoid 9  }	 
-- 1.3.6.1.4.1.15.1.3.9
-- iso(1). org(3). dod(6). internet(1). private(4). enterprises(1). xylogics(15). prod(1). prodoid(3). csmim2(9)
annex2000	OBJECT IDENTIFIER 	::= { prodoid 10  }	 
-- 1.3.6.1.4.1.15.1.3.10
-- iso(1). org(3). dod(6). internet(1). private(4). enterprises(1). xylogics(15). prod(1). prodoid(3). annex2000(10)
microcs	OBJECT IDENTIFIER 	::= { prodoid 11  }	 
-- 1.3.6.1.4.1.15.1.3.11
-- iso(1). org(3). dod(6). internet(1). private(4). enterprises(1). xylogics(15). prod(1). prodoid(3). microcs(11)
annex4000	OBJECT IDENTIFIER 	::= { prodoid 12  }	 
-- 1.3.6.1.4.1.15.1.3.12
-- iso(1). org(3). dod(6). internet(1). private(4). enterprises(1). xylogics(15). prod(1). prodoid(3). annex4000(12)
a3Com	OBJECT IDENTIFIER 	::= { prodoid 13  }	 
-- 1.3.6.1.4.1.15.1.3.13
-- iso(1). org(3). dod(6). internet(1). private(4). enterprises(1). xylogics(15). prod(1). prodoid(3). a3Com(13)
csmim-t1	OBJECT IDENTIFIER 	::= { prodoid 14  }	 
-- 1.3.6.1.4.1.15.1.3.14
-- iso(1). org(3). dod(6). internet(1). private(4). enterprises(1). xylogics(15). prod(1). prodoid(3). csmim-t1(14)
ra6100	OBJECT IDENTIFIER 	::= { prodoid 15  }	 
-- 1.3.6.1.4.1.15.1.3.15
-- iso(1). org(3). dod(6). internet(1). private(4). enterprises(1). xylogics(15). prod(1). prodoid(3). ra6100(15)
ra6300	OBJECT IDENTIFIER 	::= { prodoid 16  }	 
-- 1.3.6.1.4.1.15.1.3.16
-- iso(1). org(3). dod(6). internet(1). private(4). enterprises(1). xylogics(15). prod(1). prodoid(3). ra6300(16)
bay5391	OBJECT IDENTIFIER 	::= { prodoid 17  }	 
-- 1.3.6.1.4.1.15.1.3.17
-- iso(1). org(3). dod(6). internet(1). private(4). enterprises(1). xylogics(15). prod(1). prodoid(3). bay5391(17)
bay5393	OBJECT IDENTIFIER 	::= { prodoid 18  }	 
-- 1.3.6.1.4.1.15.1.3.18
-- iso(1). org(3). dod(6). internet(1). private(4). enterprises(1). xylogics(15). prod(1). prodoid(3). bay5393(18)
bay5399	OBJECT IDENTIFIER 	::= { prodoid 19  }	 
-- 1.3.6.1.4.1.15.1.3.19
-- iso(1). org(3). dod(6). internet(1). private(4). enterprises(1). xylogics(15). prod(1). prodoid(3). bay5399(19)
annex	OBJECT IDENTIFIER 	::= { xylogics 2  }	 
-- 1.3.6.1.4.1.15.2
-- iso(1). org(3). dod(6). internet(1). private(4). enterprises(1). xylogics(15). annex(2)
anxexperimental	OBJECT IDENTIFIER 	::= { xylogics 3  }	 
-- 1.3.6.1.4.1.15.3
-- iso(1). org(3). dod(6). internet(1). private(4). enterprises(1). xylogics(15). anxexperimental(3)
racTraps	OBJECT IDENTIFIER 	::= { xylogics 100  }	 
-- 1.3.6.1.4.1.15.100
-- iso(1). org(3). dod(6). internet(1). private(4). enterprises(1). xylogics(15). racTraps(100)
hw	OBJECT IDENTIFIER 	::= { annex 1  }	 
-- 1.3.6.1.4.1.15.2.1
-- iso(1). org(3). dod(6). internet(1). private(4). enterprises(1). xylogics(15). annex(2). hw(1)
sw	OBJECT IDENTIFIER 	::= { annex 2  }	 
-- 1.3.6.1.4.1.15.2.2
-- iso(1). org(3). dod(6). internet(1). private(4). enterprises(1). xylogics(15). annex(2). sw(2)
ports	OBJECT IDENTIFIER 	::= { annex 3  }	 
-- 1.3.6.1.4.1.15.2.3
-- iso(1). org(3). dod(6). internet(1). private(4). enterprises(1). xylogics(15). annex(2). ports(3)
parallelport	OBJECT IDENTIFIER 	::= { annex 4  }	 
-- 1.3.6.1.4.1.15.2.4
-- iso(1). org(3). dod(6). internet(1). private(4). enterprises(1). xylogics(15). annex(2). parallelport(4)
annexconfig	OBJECT IDENTIFIER 	::= { annex 5  }	 
-- 1.3.6.1.4.1.15.2.5
-- iso(1). org(3). dod(6). internet(1). private(4). enterprises(1). xylogics(15). annex(2). annexconfig(5)
annexcmds	OBJECT IDENTIFIER 	::= { annex 6  }	 
-- 1.3.6.1.4.1.15.2.6
-- iso(1). org(3). dod(6). internet(1). private(4). enterprises(1). xylogics(15). annex(2). annexcmds(6)
annexlatstats	OBJECT IDENTIFIER 	::= { annex 7  }	 
-- 1.3.6.1.4.1.15.2.7
-- iso(1). org(3). dod(6). internet(1). private(4). enterprises(1). xylogics(15). annex(2). annexlatstats(7)
interfacerip	OBJECT IDENTIFIER 	::= { annex 8  }	 
-- 1.3.6.1.4.1.15.2.8
-- iso(1). org(3). dod(6). internet(1). private(4). enterprises(1). xylogics(15). annex(2). interfacerip(8)
anxsyncports	OBJECT IDENTIFIER 	::= { annex 9  }	 
-- 1.3.6.1.4.1.15.2.9
-- iso(1). org(3). dod(6). internet(1). private(4). enterprises(1). xylogics(15). annex(2). anxsyncports(9)
anxTrapHostInfo	OBJECT IDENTIFIER 	::= { annex 10  }	 
-- 1.3.6.1.4.1.15.2.10
-- iso(1). org(3). dod(6). internet(1). private(4). enterprises(1). xylogics(15). annex(2). anxTrapHostInfo(10)
anxt1	OBJECT IDENTIFIER 	::= { annex 11  }	 
-- 1.3.6.1.4.1.15.2.11
-- iso(1). org(3). dod(6). internet(1). private(4). enterprises(1). xylogics(15). annex(2). anxt1(11)
anxpri	OBJECT IDENTIFIER 	::= { annex 12  }	 
-- 1.3.6.1.4.1.15.2.12
-- iso(1). org(3). dod(6). internet(1). private(4). enterprises(1). xylogics(15). annex(2). anxpri(12)
anxinterface	OBJECT IDENTIFIER 	::= { annex 13  }	 
-- 1.3.6.1.4.1.15.2.13
-- iso(1). org(3). dod(6). internet(1). private(4). enterprises(1). xylogics(15). annex(2). anxinterface(13)
anxtunnelport	OBJECT IDENTIFIER 	::= { annex 14  }	 
-- 1.3.6.1.4.1.15.2.14
-- iso(1). org(3). dod(6). internet(1). private(4). enterprises(1). xylogics(15). annex(2). anxtunnelport(14)
anxgrestats	OBJECT IDENTIFIER 	::= { annex 15  }	 
-- 1.3.6.1.4.1.15.2.15
-- iso(1). org(3). dod(6). internet(1). private(4). enterprises(1). xylogics(15). annex(2). anxgrestats(15)
callmgmt	OBJECT IDENTIFIER 	::= { annex 16  }	 
-- 1.3.6.1.4.1.15.2.16
-- iso(1). org(3). dod(6). internet(1). private(4). enterprises(1). xylogics(15). annex(2). callmgmt(16)
ipsec	OBJECT IDENTIFIER 	::= { annex 17  }	 
-- 1.3.6.1.4.1.15.2.17
-- iso(1). org(3). dod(6). internet(1). private(4). enterprises(1). xylogics(15). annex(2). ipsec(17)
anxModem	OBJECT IDENTIFIER 	::= { annex 100  }	 
-- 1.3.6.1.4.1.15.2.100
-- iso(1). org(3). dod(6). internet(1). private(4). enterprises(1). xylogics(15). annex(2). anxModem(100)
anxchascommon	OBJECT IDENTIFIER 	::= { annex 101  }	 
-- 1.3.6.1.4.1.15.2.101
-- iso(1). org(3). dod(6). internet(1). private(4). enterprises(1). xylogics(15). annex(2). anxchascommon(101)
anxchas	OBJECT IDENTIFIER 	::= { annex 102  }	 
-- 1.3.6.1.4.1.15.2.102
-- iso(1). org(3). dod(6). internet(1). private(4). enterprises(1). xylogics(15). annex(2). anxchas(102)
radiusClient	OBJECT IDENTIFIER 	::= { annex 103  }	 
-- 1.3.6.1.4.1.15.2.103
-- iso(1). org(3). dod(6). internet(1). private(4). enterprises(1). xylogics(15). annex(2). radiusClient(103)
anxgsystats	OBJECT IDENTIFIER 	::= { annex 104  }	 
-- 1.3.6.1.4.1.15.2.104
-- iso(1). org(3). dod(6). internet(1). private(4). enterprises(1). xylogics(15). annex(2). anxgsystats(104)
anxccpstats	OBJECT IDENTIFIER 	::= { annex 105  }	 
-- 1.3.6.1.4.1.15.2.105
-- iso(1). org(3). dod(6). internet(1). private(4). enterprises(1). xylogics(15). annex(2). anxccpstats(105)
igmp	OBJECT IDENTIFIER 	::= { annex 106  }	 
-- 1.3.6.1.4.1.15.2.106
-- iso(1). org(3). dod(6). internet(1). private(4). enterprises(1). xylogics(15). annex(2). igmp(106)
l2tp	OBJECT IDENTIFIER 	::= { annex 107  }	 
-- 1.3.6.1.4.1.15.2.107
-- iso(1). org(3). dod(6). internet(1). private(4). enterprises(1). xylogics(15). annex(2). l2tp(107)
anxPPPStats	OBJECT IDENTIFIER 	::= { annex 108  }	 
-- 1.3.6.1.4.1.15.2.108
-- iso(1). org(3). dod(6). internet(1). private(4). enterprises(1). xylogics(15). annex(2). anxPPPStats(108)
ss7	OBJECT IDENTIFIER 	::= { annex 109  }	 
-- 1.3.6.1.4.1.15.2.109
-- iso(1). org(3). dod(6). internet(1). private(4). enterprises(1). xylogics(15). annex(2). ss7(109)
ntp	OBJECT IDENTIFIER 	::= { annex 110  }	 
-- 1.3.6.1.4.1.15.2.110
-- iso(1). org(3). dod(6). internet(1). private(4). enterprises(1). xylogics(15). annex(2). ntp(110)
nfas	OBJECT IDENTIFIER 	::= { annex 111  }	 
-- 1.3.6.1.4.1.15.2.111
-- iso(1). org(3). dod(6). internet(1). private(4). enterprises(1). xylogics(15). annex(2). nfas(111)
ippool	OBJECT IDENTIFIER 	::= { annex 112  }	 
-- 1.3.6.1.4.1.15.2.112
-- iso(1). org(3). dod(6). internet(1). private(4). enterprises(1). xylogics(15). annex(2). ippool(112)
radiusConfig	OBJECT IDENTIFIER 	::= { radiusClient 1  }	 
-- 1.3.6.1.4.1.15.2.103.1
-- iso(1). org(3). dod(6). internet(1). private(4). enterprises(1). xylogics(15). annex(2). radiusClient(103). radiusConfig(1)
radiusStats	OBJECT IDENTIFIER 	::= { radiusClient 2  }	 
-- 1.3.6.1.4.1.15.2.103.2
-- iso(1). org(3). dod(6). internet(1). private(4). enterprises(1). xylogics(15). annex(2). radiusClient(103). radiusStats(2)
radiusAuthClient	OBJECT IDENTIFIER 	::= { radiusClient 3  }	 
-- 1.3.6.1.4.1.15.2.103.3
-- iso(1). org(3). dod(6). internet(1). private(4). enterprises(1). xylogics(15). annex(2). radiusClient(103). radiusAuthClient(3)
radiusAccClient	OBJECT IDENTIFIER 	::= { radiusClient 4  }	 
-- 1.3.6.1.4.1.15.2.103.4
-- iso(1). org(3). dod(6). internet(1). private(4). enterprises(1). xylogics(15). annex(2). radiusClient(103). radiusAccClient(4)
igmpconfig	OBJECT IDENTIFIER 	::= { igmp 1  }	 
-- 1.3.6.1.4.1.15.2.106.1
-- iso(1). org(3). dod(6). internet(1). private(4). enterprises(1). xylogics(15). annex(2). igmp(106). igmpconfig(1)
l2tpStats	OBJECT IDENTIFIER 	::= { l2tp 2  }	 
-- 1.3.6.1.4.1.15.2.107.2
-- iso(1). org(3). dod(6). internet(1). private(4). enterprises(1). xylogics(15). annex(2). l2tp(107). l2tpStats(2)
racTrapObjects	OBJECT IDENTIFIER 	::= { racTraps 1  }	 
-- 1.3.6.1.4.1.15.100.1
-- iso(1). org(3). dod(6). internet(1). private(4). enterprises(1). xylogics(15). racTraps(100). racTrapObjects(1)
wanTrapObj	OBJECT IDENTIFIER 	::= { racTrapObjects 1  }	 
-- 1.3.6.1.4.1.15.100.1.1
-- iso(1). org(3). dod(6). internet(1). private(4). enterprises(1). xylogics(15). racTraps(100). racTrapObjects(1). wanTrapObj(1)
modemTrapObj	OBJECT IDENTIFIER 	::= { racTrapObjects 2  }	 
-- 1.3.6.1.4.1.15.100.1.2
-- iso(1). org(3). dod(6). internet(1). private(4). enterprises(1). xylogics(15). racTraps(100). racTrapObjects(1). modemTrapObj(2)
callmgmtTrapObj	OBJECT IDENTIFIER 	::= { racTrapObjects 3  }	 
-- 1.3.6.1.4.1.15.100.1.3
-- iso(1). org(3). dod(6). internet(1). private(4). enterprises(1). xylogics(15). racTraps(100). racTrapObjects(1). callmgmtTrapObj(3)
genericTrapObj	OBJECT IDENTIFIER 	::= { racTrapObjects 4  }	 
-- 1.3.6.1.4.1.15.100.1.4
-- iso(1). org(3). dod(6). internet(1). private(4). enterprises(1). xylogics(15). racTraps(100). racTrapObjects(1). genericTrapObj(4)
ippoolconfig	OBJECT IDENTIFIER 	::= { ippool 1  }	 
-- 1.3.6.1.4.1.15.2.112.1
-- iso(1). org(3). dod(6). internet(1). private(4). enterprises(1). xylogics(15). annex(2). ippool(112). ippoolconfig(1)

END
