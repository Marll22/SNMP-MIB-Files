-- *****************************************************************
-- BDCOM-MEMORY-POOL-MIB
--
-- October 2003
--
-- Copyright (c) 2003 by BDCOM, Inc.
-- All rights reserved.
-- *****************************************************************

BDCOM-MEMORY-POOL-MIB DEFINITIONS ::= BEGIN

IMPORTS
    MODULE-IDENTITY,
    OBJECT-TYPE,
    Integer32,
    Gauge32
        FROM SNMPv2-SMI
    TEXTUAL-CONVENTION,
    DisplayString,
    TruthValue
        FROM SNMPv2-TC
    MODULE-COMPLIANCE,
    OBJECT-GROUP
        FROM SNMPv2-CONF
    bdMgmt
        FROM BDCOM-SMI
    Percent
        FROM BDCOM-QOS-PIB-MIB;

bdcomMemoryPoolMIB MODULE-IDENTITY
	LAST-UPDATED "200310160000Z"
	ORGANIZATION "BDCOM, Inc."
	CONTACT-INFO
		" Tel:   +86-21-50800666  
		 Postal: No.123,Juli RD,Zhangjiang Hitech Park,
			 Shanghai Baud Data Communication Corporation Inc,
			 Shanghai City 201203,
		 	P.R.C "
    	DESCRIPTION
        	"MIB module for monitoring memory pools"
   	REVISION        "200310160000Z"
	DESCRIPTION
		"Initial version of this MIB."
    ::= { bdMgmt 48 }

bdcomMemoryPoolUtilization OBJECT-TYPE
    SYNTAX        Percent
    MAX-ACCESS    read-only
    STATUS        current
    DESCRIPTION
        "This is the memory pool utilization"
    ::= { bdcomMemoryPoolMIB 1 }

-- notifications

bdcomMemoryPoolNotifications
    OBJECT IDENTIFIER ::= { bdcomMemoryPoolMIB 2 }

-- (no notifications are currently defined)


-- conformance information

bdcomMemoryPoolConformance
    OBJECT IDENTIFIER ::= { bdcomMemoryPoolMIB 3 }
bdcomMemoryPoolCompliances
    OBJECT IDENTIFIER ::= { bdcomMemoryPoolConformance 1 }
bdcomMemoryPoolGroups
    OBJECT IDENTIFIER ::= { bdcomMemoryPoolConformance 2 }


-- compliance statements

bdcomMemoryPoolCompliance MODULE-COMPLIANCE
    STATUS    deprecated -- superceded by bdcomMemoryPoolComplianceRev1
    DESCRIPTION
        "The compliance statement for entities which implement
        the BDCOM Memory Pool MIB"
    MODULE    -- this module
        MANDATORY-GROUPS { bdcomMemoryPoolGroup }
    ::= { bdcomMemoryPoolCompliances 1 }

bdcomMemoryPoolComplianceRev1 MODULE-COMPLIANCE
    STATUS        current
    DESCRIPTION
        "The compliance statement for entities which implement
        the BDCOM Memory Pool MIB"
    MODULE    -- this module
        MANDATORY-GROUPS { bdcomMemoryPoolGroup }

        GROUP bdcomMemoryPoolUtilizationGroup
        DESCRIPTION
            "Per memory pool utilization statistics is mandatory for
            the managed system that supports memory pool utilization."
    ::= { bdcomMemoryPoolCompliances 2 }


-- units of conformance

bdcomMemoryPoolGroup OBJECT-GROUP
    OBJECTS {
        bdcomMemoryPoolName,
        bdcomMemoryPoolAlternate,
        bdcomMemoryPoolValid,
        bdcomMemoryPoolUsed,
        bdcomMemoryPoolFree,
        bdcomMemoryPoolLargestFree
    }
    STATUS        current
    DESCRIPTION
        "A collection of objects providing memory pool monitoring."
    ::= { bdcomMemoryPoolGroups 1 }

bdcomMemoryPoolUtilizationGroup OBJECT-GROUP
    OBJECTS {
        bdcomMemoryPoolUtilization1Min,
        bdcomMemoryPoolUtilization5Min,
        bdcomMemoryPoolUtilization10Min
    }
    STATUS        current
    DESCRIPTION
        "An optional group providing a collection of memory pool
        utilization objects."
    ::= { bdcomMemoryPoolGroups 2 }


END
