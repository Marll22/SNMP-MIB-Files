-- *****************************************************************
-- BDCOM-WAN-MIB.my: BDCOM WAN MIB
--
-- March 2010
-- Edit by LIUQIANG
-- Copyright (c) 2010 by BDCOM, Inc.
-- All rights reserved.
-- *****************************************************************


BDCOM-WAN-MIB DEFINITIONS ::= BEGIN 

IMPORTS
    MODULE-IDENTITY, OBJECT-TYPE, NOTIFICATION-TYPE,INTEGER
                                                FROM SNMPv2-SMI
    TEXTUAL-CONVENTION                          FROM SNMPv2-TC
    MODULE-COMPLIANCE, OBJECT-GROUP             FROM SNMPv2-CONF
    ifIndex                            FROM RFC1213-MIB
    IpAddress   				FROM RFC1155-SMI
    bdMgmt                             FROM BDCOM-SMI;

--definition of BDCOM device wan information

               	wan         OBJECT IDENTIFIER ::= { bdMgmt 356 }

               bdWanIfTable OBJECT-TYPE
                   SYNTAX  SEQUENCE OF BdWanIfEntry
                   ACCESS  not-accessible
                   STATUS  mandatory
                   DESCRIPTION
                           "BDCOM WAN interface table."
                   ::= { wan 1 }
        
               bdWanIfEntry OBJECT-TYPE
                   SYNTAX  BdWanIfEntry
                   ACCESS  not-accessible
                   STATUS  mandatory
                   DESCRIPTION
                           "BDCOM WAN interface table entry."
                   INDEX   { ifIndex }
                   ::= { bdWanIfTable 1 }
        
               BdWanIfEntry ::=
                   SEQUENCE {
                       bdWanIfConnType
                           INTEGER,
                       bdWanIfIpAddr
                           IpAddress,
                       bdWanIfMask
                           IpAddress,
                       bdWanIfDefaultGateway
                           IpAddress,
                       bdWanIfMasterDNS
                           IpAddress,
                       bdWanIfSlaveDNS
                           IpAddress,
                       bdWanIfMTU
                           INTEGER
                   }

               
               bdWanIfConnType OBJECT-TYPE
                   SYNTAX  INTEGER
                   ACCESS  read-only
                   STATUS  mandatory
                   DESCRIPTION
                           "BDCOM WAN interface connection type. This type is temporarily unknown"
                   ::= { bdWanIfEntry 1 }
               
               bdWanIfIpAddr OBJECT-TYPE
                   SYNTAX  IpAddress
                   ACCESS  read-only
                   STATUS  mandatory
                   DESCRIPTION
                           "BDCOM WAN interface IP address, the same value as ipAdEntAddr in ipAddrTable."
                   ::= { bdWanIfEntry 2 }
               
               bdWanIfMask OBJECT-TYPE
                   SYNTAX  IpAddress
                   ACCESS  read-only
                   STATUS  mandatory
                   DESCRIPTION
                           "BDCOM WAN interface mask, the same value as ipAdEntNetMask in ipAddrTable."
                   ::= { bdWanIfEntry 3 }
               
               bdWanIfDefaultGateway OBJECT-TYPE
                   SYNTAX  IpAddress
                   ACCESS  read-only
                   STATUS  mandatory
                   DESCRIPTION
                           "BDCOM WAN interface default gateway."
                   ::= { bdWanIfEntry 4 }
               
               bdWanIfMasterDNS OBJECT-TYPE
                   SYNTAX  IpAddress
                   ACCESS  read-only
                   STATUS  mandatory
                   DESCRIPTION
                           "BDCOM WAN interface master DNS address."
                   ::= { bdWanIfEntry 5 }
               
               bdWanIfSlaveDNS OBJECT-TYPE
                   SYNTAX  IpAddress
                   ACCESS  read-only
                   STATUS  mandatory
                   DESCRIPTION
                           "BDCOM WAN interface slave DNS address."
                   ::= { bdWanIfEntry 6 }

               bdWanIfMTU OBJECT-TYPE
                   SYNTAX  INTEGER
                   ACCESS  read-only
                   STATUS  mandatory
                   DESCRIPTION
                           "BDCOM WAN interface MTU value, the same value as ifMTU in ifTable."
                   ::= { bdWanIfEntry 7 }
               
               
               
               
END
