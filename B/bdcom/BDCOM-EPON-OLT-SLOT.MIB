-- *****************************************************************
-- BDCOM-EPON-OLT-SLOT.MIB:  BDCom OLT-SLOT MIB file
-- OCT 2009
-- *****************************************************************
--

               BDCOM-EPON-OLT-SLOT DEFINITIONS ::= BEGIN

               IMPORTS
                    Counter, IpAddress, Counter
			FROM RFC1155-SMI
		    OBJECT-TYPE
			FROM RFC-1212
                    DisplayString, ifIndex
			FROM RFC1213-MIB
		    bdEPONGroup
			FROM BDCOM-SMI
		    RowStatus
		    	FROM SNMPv2-TC;
          
               bdEponOltSlot         OBJECT IDENTIFIER ::= { bdEPONGroup 21 }
               
               bdEponOltSlotTable OBJECT-TYPE
                   SYNTAX  SEQUENCE OF BdEponOltSlotEntry
                   ACCESS  not-accessible
                   STATUS  mandatory
                   DESCRIPTION
                            "A list of epon Olt slot table entries."
                   ::= { bdEponOltSlot 1 }

               bdEponOltSlotEntry OBJECT-TYPE
                   SYNTAX BdEponOltSlotEntry
                   ACCESS  not-accessible
                   STATUS  mandatory
                   DESCRIPTION
                            "A collection of additional objects in the
                            epon Olt slot table."
                   INDEX { oltSlotIndex }
               ::= { bdEponOltSlotTable 1 }

               BdEponOltSlotEntry ::=
                   SEQUENCE {
                       oltSlotIndex
                           INTEGER,
                       oltSlotHelloInterval
                           INTEGER,
		       oltSlotDeadInterval
                           INTEGER,
		       oltSlotChipsRegisteredNumber
                           INTEGER
		}          
          
          
               
          oltSlotIndex OBJECT-TYPE
              SYNTAX  INTEGER
              ACCESS  read-only
              STATUS  mandatory
              DESCRIPTION
                      "Slot index, which is the same value as bdcardIfCardIndex in bdcardIfIndexTable."
              ::= { bdEponOltSlotEntry 1 }
               
          oltSlotHelloInterval OBJECT-TYPE
              SYNTAX  INTEGER
              ACCESS  read-only
              STATUS  mandatory
              DESCRIPTION
                      "Package sending interval between OLT chip and card CPU."
              ::= { bdEponOltSlotEntry 2 }
               
          oltSlotDeadInterval OBJECT-TYPE
              SYNTAX  INTEGER
              ACCESS  read-only
              STATUS  mandatory
              DESCRIPTION
                      "Package timeout interval between OLT chip and card CPU."
              ::= { bdEponOltSlotEntry 3 }
               
          oltSlotChipsRegisteredNumber OBJECT-TYPE
              SYNTAX  INTEGER
              ACCESS  read-only
              STATUS  mandatory
              DESCRIPTION
                      "Number of registered OLT chips."
              ::= { bdEponOltSlotEntry 4 }
               
END
