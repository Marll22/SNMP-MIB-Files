-- *****************************************************************
-- BDCOM-EPON-OLT-PSG.MIB:  BDCom OLT-PSG MIB file
-- AUG 2009
-- *****************************************************************
--

               BDCOM-EPON-OLT-PSG DEFINITIONS ::= BEGIN

               IMPORTS
                    Counter, IpAddress, Counter
			FROM RFC1155-SMI
		    OBJECT-TYPE
			FROM RFC-1212
		    RowStatus
                        FROM SNMPv2-TC
                    DisplayString, ifIndex, PhysAddress,ifDescr
			FROM RFC1213-MIB
		    onuActivePonDiid
			FROM BDCOM-EPON-ONU
		    bdEPONGroup
			FROM BDCOM-SMI;
          
               bdEponOltPsg        OBJECT IDENTIFIER ::= { bdEPONGroup 7 }

               bdeponoltpsgTable OBJECT-TYPE
                   SYNTAX  SEQUENCE OF BdEponOltPsgEntry
                   ACCESS  not-accessible
                   STATUS  mandatory
                   DESCRIPTION
                            "A list of epon olt PSG table entries."
                   ::= { bdEponOltPsg 1 }

               bdEponOltPsgEntry OBJECT-TYPE
                   SYNTAX BdEponOltPsgEntry
                   ACCESS  not-accessible
                   STATUS  mandatory
                   DESCRIPTION
                            "A collection of additional objects in the
                            epon olt PSG table."
                   INDEX { psgDiid }
               ::= { bdeponoltpsgTable 1 }

               BdEponOltPsgEntry ::=
                   SEQUENCE {
                       psgDiid
                           INTEGER,
                       psgIfDescr
                           OCTET STRING,
                       activeEponDiid
                           INTEGER,
                       standbyEponDiid
                           INTEGER,
                       currentActiveEponDiid
                           INTEGER,
                       currentActiveEponIfDescr
                           OCTET STRING,
                       currentStandbyEponDiid
                           INTEGER,
                       currentStandbyEponIfDescr
                           OCTET STRING,
                       psgRowStatus
                           RowStatus
                   }

               psgDiid OBJECT-TYPE
                   SYNTAX  INTEGER
                   ACCESS  read-only
                   STATUS  mandatory
                   DESCRIPTION
                           "PSG diid,unique in devices."
                   ::= { bdEponOltPsgEntry 1 } 

               psgIfDescr OBJECT-TYPE
                   SYNTAX  OCTET STRING
                   ACCESS  read-only
                   STATUS  mandatory
                   DESCRIPTION
                           "PSG port description in device."
                   ::= { bdEponOltPsgEntry 2 } 

               activeEponDiid OBJECT-TYPE
                   SYNTAX  INTEGER
                   ACCESS  read-write
                   STATUS  mandatory
                   DESCRIPTION
                           "active EPON port id in PSG."
                   ::= { bdEponOltPsgEntry 3 } 

               standbyEponDiid OBJECT-TYPE
                   SYNTAX  INTEGER
                   ACCESS  read-write
                   STATUS  mandatory
                   DESCRIPTION
                           "standby EPON port id in PSG."
                   ::= { bdEponOltPsgEntry 4 } 

               currentActiveEponDiid OBJECT-TYPE
                   SYNTAX  INTEGER
                   ACCESS  read-only
                   STATUS  mandatory
                   DESCRIPTION
                           "Current active EPON port id in PSG."
                   ::= { bdEponOltPsgEntry 5 } 

               currentActiveEponIfDescr OBJECT-TYPE
                   SYNTAX  OCTET STRING
                   ACCESS  read-only
                   STATUS  mandatory
                   DESCRIPTION
                           "Current active EPON port description in PSG."
                   ::= { bdEponOltPsgEntry 6 } 

               currentStandbyEponDiid OBJECT-TYPE
                   SYNTAX  INTEGER
                   ACCESS  read-only
                   STATUS  mandatory
                   DESCRIPTION
                           "Current standby EPON port id in PSG."
                   ::= { bdEponOltPsgEntry 7 } 

               currentStandbyEponIfDescr OBJECT-TYPE
                   SYNTAX  OCTET STRING
                   ACCESS  read-only
                   STATUS  mandatory
                   DESCRIPTION
                           "Current standby EPON port description in PSG."
                   ::= { bdEponOltPsgEntry 8 } 

               psgRowStatus OBJECT-TYPE
                   SYNTAX  RowStatus
                   ACCESS  read-create
                   STATUS  mandatory
                   DESCRIPTION
                           "Row status,that a row could be created in PSG."
                   ::= { bdEponOltPsgEntry 9 } 
                   
                   
                   
               bdEponOltPsgCreateTable OBJECT-TYPE
                   SYNTAX  SEQUENCE OF BdEponOltPsgCreateEntry
                   ACCESS  not-accessible
                   STATUS  mandatory
                   DESCRIPTION
                            "A list of epon olt PSG port create table entries."
                   ::= { bdEponOltPsg 2 }

               bdEponOltPsgCreateEntry OBJECT-TYPE
                   SYNTAX BdEponOltPsgCreateEntry
                   ACCESS  not-accessible
                   STATUS  mandatory
                   DESCRIPTION
                            "A collection of additional objects in the
                            epon olt PSG port create table."
                   INDEX { psgDiid }
               ::= { bdEponOltPsgCreateTable 1 }
              

               BdEponOltPsgCreateEntry ::=
                   SEQUENCE {
                       psgPortSlotNo
                           INTEGER,
                       psgPortSeqencelNo
                           INTEGER,
                       psgPortDiid
                           INTEGER,
                       psgPortOper
                           INTEGER,
                       psgPortType
                           INTEGER
                      
                   }

               psgPortSlotNo OBJECT-TYPE
                   SYNTAX  INTEGER
                   ACCESS  read-only
                   STATUS  mandatory
                   DESCRIPTION
                           "PSG port slot number, the same value as chassis-mib slot number."
                   ::= { bdEponOltPsgCreateEntry 1 } 

               psgPortSeqencelNo OBJECT-TYPE
                   SYNTAX  INTEGER
                   ACCESS  read-only
                   STATUS  mandatory
                   DESCRIPTION
                           "PSG port sequence number, the different value in different slot."
                   ::= { bdEponOltPsgCreateEntry 2 } 

               psgPortDiid OBJECT-TYPE
                   SYNTAX  INTEGER
                   ACCESS  read-only
                   STATUS  mandatory
                   DESCRIPTION
                           "PSG port diid, the same value as ifIndex in RFC-1213."
                   ::= { bdEponOltPsgCreateEntry 3 } 

               psgPortOper OBJECT-TYPE
                   SYNTAX  INTEGER{
                            create(1),
                            delete(2),
                            switch(3)
                                  }
                   ACCESS  read-only
                   STATUS  mandatory
                   DESCRIPTION
                           "PSG port operation, 1-ceate a new psg port, 2-delete a current psg port, 3-switch between active port and standby port."
                   ::= { bdEponOltPsgCreateEntry 4 } 
                   
               psgPortType OBJECT-TYPE
                   SYNTAX  INTEGER{
                            b_psg(1),
                            c_psg(2)
                                  }
                   ACCESS  read-write
                   STATUS  mandatory
                   DESCRIPTION
                           "PSG port operation, 1-b-psg a new psg port, 2-c-psg a current psg port, 3-switch between active port and standby port."
                   ::= { bdEponOltPsgCreateEntry 5 } 
              



--psg trap Notifications
	bdEponPsgNotifications OBJECT IDENTIFIER
                                ::= { bdEponOltPsg 3 }


	bdEponPsgNotification NOTIFICATION-TYPE
    		OBJECTS {
                       psgDiid,
                       ifDescr,
                       currentActiveEponDiid,
                       currentActiveEponIfDescr,
                       currentStandbyEponDiid,
                       currentStandbyEponIfDescr
    		}
    		STATUS      current
    		DESCRIPTION
        	"The agent generates this notification when optical interface upload/download power exceed the threshold ruled in opticalPortPowerTable."
    		::= { bdEponPsgNotifications 1 }

--psg trap Notifications
	bdEponPsgSwitchNotifications OBJECT IDENTIFIER
                                ::= { bdEponOltPsg 4 }


	bdEponPsgSwitchNotification NOTIFICATION-TYPE
    		OBJECTS {
                       ifIndex,
                       ifDescr,
                       psgDiid,
                       psgIfDescr,
                       currentActiveEponDiid,
                       currentActiveEponIfDescr,
                       currentStandbyEponDiid,
                       currentStandbyEponIfDescr
    		}
    		STATUS      current
    		DESCRIPTION
        	"The agent generates this notification when psg interface switches."
    		::= { bdEponPsgSwitchNotifications 1 }







END
