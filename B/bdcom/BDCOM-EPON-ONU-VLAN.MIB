-- *****************************************************************
-- BDCOM-EPON-ONU-VLAN.MIB:  BDCom LLID ONU VLAN MIB file
-- AUG 2009
-- *****************************************************************
--

               BDCOM-EPON-ONU-VLAN DEFINITIONS ::= BEGIN

               IMPORTS
                    Counter, IpAddress, Counter
			FROM RFC1155-SMI
		    OBJECT-TYPE
			FROM RFC-1212
                    DisplayString
			FROM RFC1213-MIB
		    bdEPONGroup
			FROM BDCOM-SMI
		    TruthValue,RowStatus,PhysAddress,DisplayString,MacAddress
		    	FROM SNMPv2-TC;
          
               bdEponOnuVlan         OBJECT IDENTIFIER ::= { bdEPONGroup 13 }
               
               bdepononuvlanTable OBJECT-TYPE
                   SYNTAX  SEQUENCE OF BdEponOnuVlanEntry
                   ACCESS  not-accessible
                   STATUS  mandatory
                   DESCRIPTION
                            "A list of epon ONU port vlan table entries."
                   ::= { bdEponOnuVlan 1 }

               bdEponOnuVlanEntry OBJECT-TYPE
                   SYNTAX  BdEponOnuVlanEntry
                   ACCESS  not-accessible
                   STATUS  mandatory
                   DESCRIPTION
                            "A collection of additional objects in the
                            epon ONU port vlan property table."
                   INDEX { onuLlidDiid,onuIfSequenceNo }
               ::= { bdepononuvlanTable 1 }

               BdEponOnuVlanEntry ::=
                   SEQUENCE {
                       onuLlidDiid
                           INTEGER,
                       onuIfSequenceNo
                           INTEGER,
                       onuOldVlan
                           INTEGER,
                       onuNewVlan
                           INTEGER
			}
			
               onuLlidDiid OBJECT-TYPE
                   SYNTAX  INTEGER
                   ACCESS  read-only
                   STATUS  mandatory
                   DESCRIPTION
                           "LLID port DIID, as one of the index together with onuIfSequenceNo."
                   ::= { bdEponOnuVlanEntry 1 } 

               onuIfSequenceNo OBJECT-TYPE
                   SYNTAX  INTEGER
                   ACCESS  read-only
                   STATUS  mandatory
                   DESCRIPTION
                           "ONU interface sequence number, as one of the index together with onuLlidDiid."
                   ::= { bdEponOnuVlanEntry 2 } 
		
               onuOldVlan OBJECT-TYPE
                   SYNTAX  INTEGER(1..4094)
                   ACCESS  read-write
                   STATUS  mandatory
                   DESCRIPTION
                           "ONU interface old vlan id. This configuration can be set only as vlan mode is translation mode."
                   ::= { bdEponOnuVlanEntry 3 } 
		
               onuNewVlan OBJECT-TYPE
                   SYNTAX  INTEGER(1..4094)
                   ACCESS  read-write
                   STATUS  mandatory
                   DESCRIPTION
                           "ONU interface new vlan id. This configuration can be set only as vlan mode is translation mode."
                   ::= { bdEponOnuVlanEntry 4 } 
		

			
END
