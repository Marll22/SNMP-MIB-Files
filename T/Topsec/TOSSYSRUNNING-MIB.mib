-- ***************************************************
-- for 1130-D8006 custom made
-- ***************************************************
TOSSYSRUNNING-MIB DEFINITIONS ::= BEGIN

IMPORTS
	enterprises
            FROM RFC1155-SMI
	DisplayString
            FROM SNMPv2-TC
	Integer32
			FROM SNMPv2-SMI;

	-- 1.3.6.1.4.1.14331
	topsec MODULE-IDENTITY
	    LAST-UPDATED "15-06-17" 
	    ORGANIZATION "TOPSEC"
	    CONTACT-INFO
	            " Topsec Beijing
	              China
	              E-mail: support@topsec.com.cn "
	    DESCRIPTION
	            "The MIB module for management of Topsec Operating System Security Product, independent of the specific encapsulation scheme in use."
	    REVISION     "05-09-14" 
	    DESCRIPTION
	            "Initial version."
	    REVISION    "20060809"
	    DESCRIPTION
	            "enterprises revised."
	    REVISION    "20061020"
	    DESCRIPTION
	            "Mgmt revised."
	    REVISION    "20070927"
	    DESCRIPTION
	            "ivtable;some other object changed ."
	    REVISION	"20150706"
	    DESCRIPTION
	    		"For 1130-ads custom made,Delete all objects without cpuLoad¡¢memoryLoad¡¢diskSize."
	    ::= { enterprises 14331 }
		
	-- 1.3.6.1.4.1.14331.5
	topsecMgmt	OBJECT IDENTIFIER ::= { topsec 5 }
	-- 1.3.6.1.4.1.14331.5.5
	objects			OBJECT IDENTIFIER ::= { topsecMgmt 5 }
	-- 1.3.6.1.4.1.14331.5.5.1
	tosMib	OBJECT IDENTIFIER ::= { objects 1 }
	-- 1.3.6.1.4.1.14331.5.5.1.4
	sysrunning	OBJECT IDENTIFIER ::= { tosMib 4 }   

	cpuLoad OBJECT-TYPE
	    SYNTAX      Integer32
	    MAX-ACCESS  read-only
	    STATUS      current
	    DESCRIPTION
	            "CPU load value (percent*100)."
	    ::= { sysrunning 5 }

	memoryLoad OBJECT-TYPE
	    SYNTAX      Integer32 
	    MAX-ACCESS  read-only
	    STATUS      current
	    DESCRIPTION
	            "Memory load value (percent*100)."
	    ::= { sysrunning 6 }    
	    
	cursessiontotal OBJECT-TYPE
	    SYNTAX      Counter 
	    MAX-ACCESS  read-only
	    STATUS      current
	    DESCRIPTION
	            "The total number of the firewall concurrent session."   
	    ::= { sysrunning 11 }  
	    
	cursessionrate OBJECT-TYPE
	    SYNTAX      Counter 
	    MAX-ACCESS  read-only
	    STATUS      current
	    DESCRIPTION
	            "The count of build session per second."
	    ::= { sysrunning 12 } 	       
	    	
END
