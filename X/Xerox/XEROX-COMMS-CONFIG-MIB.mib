XEROX-COMMS-CONFIG-MIB DEFINITIONS ::= BEGIN

--  Module: Communications Configuration MIB
--  Author: Ira McDonald, Alan Sullivan, Robert Westfall
--  File:   53config.mib
--  Date:   4 September 1997 - Version 2.32.pub

IMPORTS
    MODULE-IDENTITY, OBJECT-TYPE,
        Integer32
            FROM SNMPv2-SMI             -- IETF RFC 1442/1902
    RowStatus
            FROM SNMPv2-TC              -- IETF RFC 1443/1903
    MODULE-COMPLIANCE, OBJECT-GROUP
            FROM SNMPv2-CONF            -- IETF RFC 1444/1904
    hrDeviceIndex
            FROM HOST-RESOURCES-MIB     -- IETF RFC 1514
    CodedCharSet
            FROM Printer-MIB            -- IETF RFC 1759
    xeroxCommonMIB
            FROM XEROX-COMMON-MIB
    Ordinal32, Cardinal32,
        XcmGenOptionValueSyntax,
        xcmGenZeroDotZero
            FROM XEROX-GENERAL-TC
    XcmCommsConfigGroupSupport
            FROM XEROX-COMMS-CONFIG-TC;

xcmCommsConfigMIB MODULE-IDENTITY
    LAST-UPDATED "9709040000Z"
    ORGANIZATION "Xerox Corporation - XCMI Working Group"
    CONTACT-INFO
        "           XCMI Editors
        Email:      xcmieditors@cp10.es.xerox.com

        --
        --
        "
    DESCRIPTION
        "Version:   2.32.pub

        The MIB module which supports active configuration discovery
        of communications protocol stacks, communications end system
        applications, communications intermediate systems, and
        communications gateways for network accessible host systems.

        Usage:  Note that throughout this MIB module, the INDEX clauses
        referring to 'hrDeviceIndex' for the 'hrDeviceTable' (Devices
        Group) of the Host Resources MIB (RFC 1514) shall ALWAYS
        specify host system CPUs (ie, 'hrDeviceProcessor') and shall NOT
        specify host system 'network interfaces', with entries in the
        'ifTable' (Interfaces Group) of MIB-II (RFC 1213).

        Copyright (C) 1997 Xerox Corporation. All Rights Reserved."
    ::= { xeroxCommonMIB 64 }

--
--          Comms Config MIB
--
--          Comms Config Group (Mandatory)
--
--          Implementation of this group is mandatory for all systems

xcmCommsConfig          OBJECT IDENTIFIER ::= { xcmCommsConfigMIB 3 }

xcmCommsConfigTable OBJECT-TYPE
    SYNTAX      SEQUENCE OF XcmCommsConfigEntry
    MAX-ACCESS  not-accessible
    STATUS      current


    DESCRIPTION
        "A table of the communications engines installed and (possibly)
        running on platforms (ie, CPUs) on this host system."
    ::= { xcmCommsConfig 2 }

xcmCommsConfigEntry OBJECT-TYPE
    SYNTAX      XcmCommsConfigEntry
    MAX-ACCESS  not-accessible
    STATUS      current
    DESCRIPTION
        "An entry for a communications engine installed and (possibly)
        running on a platform (ie, CPU) on this host system.

        Usage:  Note that values of 'hrDeviceIndex' used to reference
        entries in the 'xcmCommsEngineTable' shall ALWAYS reference
        entries in the 'hrDeviceTable' with 'hrDeviceType' equal to
        'hrDeviceProcessor' (representing host system CPUs and therefore
        also having corresponding entries in the 'hrProcessorTable')."
    INDEX       { hrDeviceIndex }
    ::= { xcmCommsConfigTable 1 }

XcmCommsConfigEntry ::= SEQUENCE {
        --  Comms Config Information
        xcmCommsConfigRowStatus         RowStatus,
        xcmCommsConfigActiveOptionFirst Cardinal32,
        xcmCommsConfigActiveOptionLast  Cardinal32,
        xcmCommsConfigGroupSupport      XcmCommsConfigGroupSupport,
        xcmCommsConfigCreateSupport     XcmCommsConfigGroupSupport,
        xcmCommsConfigUpdateSupport     XcmCommsConfigGroupSupport
    }

--
--          Comms Config Information
--

xcmCommsConfigRowStatus OBJECT-TYPE
    SYNTAX      RowStatus
    MAX-ACCESS  read-only
    STATUS      current
    DESCRIPTION
        "This object is used to create and delete individual conceptual
        rows in the 'xcmCommsConfigTable'."
    ::= { xcmCommsConfigEntry 1 }

xcmCommsConfigActiveOptionFirst OBJECT-TYPE
    SYNTAX      Cardinal32
    MAX-ACCESS  read-only
    STATUS      current
    DESCRIPTION
        "The value of 'xcmCommsOptionIndex' corresponding to the first
        active configuration option (in 'xcmCommsOptionTable'), or zero
        if this communications engine does NOT require such information.

        Usage:  This 'chain' represents currently active configuration


        options of this communications engine."
    REFERENCE
        "See:   'xcmCommsConfigActiveOptionLast'"
    DEFVAL      { 0 }                   -- no entries
    ::= { xcmCommsConfigEntry 2 }

xcmCommsConfigActiveOptionLast OBJECT-TYPE
    SYNTAX      Cardinal32
    MAX-ACCESS  read-only
    STATUS      current
    DESCRIPTION
        "The value of 'xcmCommsOptionIndex' corresponding to the last
        active configuration option (in 'xcmCommsOptionTable'), or zero
        if this communications engine does NOT require such information.

        Usage:  This 'chain' represents currently active configuration
        options of this communications engine.

        Usage:  The last entry index explicitly bounds the valid range
        of 'xcmCommsOptionIndex'."
    REFERENCE
        "See:   'xcmCommsConfigActiveOptionFirst'"
    DEFVAL      { 0 }                   -- no entries
    ::= { xcmCommsConfigEntry 3 }

xcmCommsConfigGroupSupport OBJECT-TYPE
    SYNTAX      XcmCommsConfigGroupSupport
    MAX-ACCESS  read-only
    STATUS      current
    DESCRIPTION
        "The terse conformance statement of ALL mandatory, conditionally
        mandatory, and optional XCMI Comms Config MIB object groups
        supported by this management agent implementation (ie, version)
        on this host system, specified in a bit-mask.

        Usage:  Conforming management agents shall ALWAYS accurately
        report their support for XCMI Comms Config MIB object groups."
    DEFVAL      { 1 }                   -- mandatory groups
    ::= { xcmCommsConfigEntry 4 }

xcmCommsConfigCreateSupport OBJECT-TYPE
    SYNTAX      XcmCommsConfigGroupSupport
    MAX-ACCESS  read-only
    STATUS      current
    DESCRIPTION
        "The terse conformance statement of ALL mandatory, conditionally
        mandatory, and optional XCMI Comms Config MIB object groups
        supported for dynamic row creation (via '...RowStatus')
        by this management agent implementation (ie, version)
        on this host system, specified in a bit-mask.

        Usage:  Conforming management agents shall ALWAYS accurately
        report their support for XCMI Comms Config MIB object groups."
    DEFVAL      { 0 }                   -- no dynamic row create groups


    ::= { xcmCommsConfigEntry 5 }

xcmCommsConfigUpdateSupport OBJECT-TYPE
    SYNTAX      XcmCommsConfigGroupSupport
    MAX-ACCESS  read-only
    STATUS      current
    DESCRIPTION
        "The terse conformance statement of ALL mandatory, conditionally
        mandatory, and optional XCMI Comms Config MIB object groups
        supported for existing row update (via SNMP Set-Request PDUs)
        by this management agent implementation (ie, version)
        on this host system, specified in a bit-mask.

        Usage:  Conforming management agents shall ALWAYS accurately
        report their support for XCMI Comms Config MIB object groups."
    DEFVAL      { 0 }                   -- no existing row update groups
    ::= { xcmCommsConfigEntry 6 }

--
--          Comms Option Group (Mandatory)
--
--          Implementation of this group is mandatory for all systems.

xcmCommsOption          OBJECT IDENTIFIER ::= { xcmCommsConfigMIB 4 }

xcmCommsOptionTable OBJECT-TYPE
    SYNTAX      SEQUENCE OF XcmCommsOptionEntry
    MAX-ACCESS  not-accessible
    STATUS      current
    DESCRIPTION
        "A table containing information on installation, configuration,
        or other aspects of communications options on this host system."
    ::= { xcmCommsOption 2 }

xcmCommsOptionEntry OBJECT-TYPE
    SYNTAX      XcmCommsOptionEntry
    MAX-ACCESS  not-accessible
    STATUS      current
    DESCRIPTION
        "An entry containing information on installation, configuration,
        or other aspects of communications options on this host system."
    INDEX       { hrDeviceIndex, xcmCommsOptionIndex }
    ::= { xcmCommsOptionTable 1 }

XcmCommsOptionEntry ::= SEQUENCE {
        --  Comms Option Information
        xcmCommsOptionIndex             Ordinal32,
        xcmCommsOptionRowStatus         RowStatus,
        xcmCommsOptionTypeOID           OBJECT IDENTIFIER,
        xcmCommsOptionValueSyntax       XcmGenOptionValueSyntax,
        xcmCommsOptionValueInteger      Integer32,
        xcmCommsOptionValueOID          OBJECT IDENTIFIER,
        xcmCommsOptionValueString       OCTET STRING,
        xcmCommsOptionValueLocalization Cardinal32,


        xcmCommsOptionValueCodedCharSet CodedCharSet,
        --  Comms Option Common Cross References
        xcmCommsOptionNextIndex         Cardinal32,
        xcmCommsOptionPreviousIndex     Cardinal32,
        xcmCommsOptionFamilyIndex       Cardinal32
    }

--
--          Comms Option Information
--

xcmCommsOptionIndex OBJECT-TYPE
    SYNTAX      Ordinal32
    MAX-ACCESS  not-accessible
    STATUS      current
    DESCRIPTION
        "A unique value used by this host system to identify this
        conceptual row in the 'xcmCommsOptionTable'."
    ::= { xcmCommsOptionEntry 1 }

xcmCommsOptionRowStatus OBJECT-TYPE
    SYNTAX      RowStatus
    MAX-ACCESS  read-only
    STATUS      current
    DESCRIPTION
        "This object is used to create and delete individual conceptual
        rows in the 'xcmCommsOptionTable'."
    ::= { xcmCommsOptionEntry 2 }

xcmCommsOptionTypeOID OBJECT-TYPE
    SYNTAX      OBJECT IDENTIFIER
    MAX-ACCESS  read-only
    STATUS      current
    DESCRIPTION
        "An unambiguous communications option type,
        used by system administrators and end users to identify
        this communications option.

        Usage:  Since this communications option type is specified
        as an object identifier, it may be taken from any IETF, Xerox,
        third- party, or product-specific MIB, or it may simply be any
        IETF SMIv2-style 'autonomous type'."
    DEFVAL      { xcmGenZeroDotZero }   -- no option type
    ::= { xcmCommsOptionEntry 3 }

xcmCommsOptionValueSyntax OBJECT-TYPE
    SYNTAX      XcmGenOptionValueSyntax
    MAX-ACCESS  read-only
    STATUS      current
    DESCRIPTION
        "A communications option value syntax,
        used by system administrators and end users to specify
        the correct value syntax for this communications option.


        Usage:  This communications option value syntax is used to
        select which of the following three objects shall be used to
        contain the value of this communications option."
    DEFVAL      { unknown }             -- unknown option value syntax
    ::= { xcmCommsOptionEntry 4 }

xcmCommsOptionValueInteger OBJECT-TYPE
    SYNTAX      Integer32
    MAX-ACCESS  read-only
    STATUS      current
    DESCRIPTION
        "A communications option value integer,
        used by system administrators and end users to specify
        the current value for a communications option
        with a base value syntax of 'INTEGER'."
    REFERENCE
        "See:   'xcmCommsOptionValueSyntax' and 'xcmCommsOptionTypeOID'"
    DEFVAL      { 0 }                   -- no option value integer
    ::= { xcmCommsOptionEntry 5 }

xcmCommsOptionValueOID OBJECT-TYPE
    SYNTAX      OBJECT IDENTIFIER
    MAX-ACCESS  read-only
    STATUS      current
    DESCRIPTION
        "A communications option value OID (object identifier),
        used by system administrators and end users to specify
        the current value for a communications option
        with a base value syntax of 'OBJECT IDENTIFIER'."
    REFERENCE
        "See:   'xcmCommsOptionValueSyntax' and 'xcmCommsOptionTypeOID'"
    DEFVAL      { xcmGenZeroDotZero }   -- no option value OID
    ::= { xcmCommsOptionEntry 6 }

xcmCommsOptionValueString OBJECT-TYPE
    SYNTAX      OCTET STRING (SIZE (0..255))
    MAX-ACCESS  read-only
    STATUS      current
    DESCRIPTION
        "A communications option value string,
        used by system administrators and end users to specify
        the current value for a communications option
        with a base value syntax of 'OCTET STRING'."
    REFERENCE
        "See:   'xcmCommsOptionValueSyntax' and 'xcmCommsOptionTypeOID'"
    DEFVAL      { ''H }                 -- no option value string
    ::= { xcmCommsOptionEntry 7 }

xcmCommsOptionValueLocalization OBJECT-TYPE
    SYNTAX      Cardinal32
    MAX-ACCESS  read-only
    STATUS      current
    DESCRIPTION


        "A communications option value localization,
        used by system administrators and end users to specify
        the static localization for a communications option
        with a base value syntax of 'OCTET STRING'.

        Usage:  For a communications option string to which POSIX-style
        localization (territory, language, character set) is applicable,
        this object shall ALWAYS contain a suitable index value for
        'xcmGenLocalizationIndex' from the XCMI General MIB, or zero to
        indicate 'none'."
    REFERENCE
        "See:   'xcmCommsOptionValueSyntax' and 'xcmCommsOptionTypeOID'"
    DEFVAL      { 0 }                   -- no option value localization
    ::= { xcmCommsOptionEntry 8 }

xcmCommsOptionValueCodedCharSet OBJECT-TYPE
    SYNTAX      CodedCharSet
    MAX-ACCESS  read-only
    STATUS      current
    DESCRIPTION
        "A communications option value character set,
        used by system administrators and end users to specify
        the current character set for a communications option
        with a base value syntax of 'OCTET STRING'.

        Usage:  For a communications option string to which ONLY
        character set conversion (and NOT territory or language aspects
        of 'localization') is applicable, this object shall ALWAYS
        contain a suitable value or 'other(1)' to indicate 'none' or
        not currently standardized and enumerated in 'CodedCharSet'.
        The 'CodedCharSet' textual convention is defined in the IETF
        Printer MIB (RFC 1759)."
    REFERENCE
        "See:   'xcmCommsOptionValueSyntax' and 'xcmCommsOptionTypeOID'"
    DEFVAL      { other }               -- no option value character set
    ::= { xcmCommsOptionEntry 9 }

--
--          Comms Option Common Cross References
--

xcmCommsOptionNextIndex OBJECT-TYPE
    SYNTAX      Cardinal32
    MAX-ACCESS  read-only
    STATUS      current
    DESCRIPTION
        "The value of 'xcmCommsOptionIndex' corresponding to the next
        'chained' conceptual row in the 'xcmCommsOptionTable', or zero
        if this is the last associated conceptual row in a particular
        vertical 'chain' within a given set.

        Usage:  Generally, communications options (of similar or unlike
        type) are 'chained' vertically via '...[Next|Previous]Index'.
        But, in the case where particular communications options MUST


        be 'tightly coupled', they should be 'shelved' horizontally via
        '...[Family|Previous]Index' (eg, an IP address and an IP subnet
        mask)."
    REFERENCE
        "See:   'xcmCommsOption[Family|Previous]Index'"
    DEFVAL      { 0 }                   -- no entry
    ::= { xcmCommsOptionEntry 10 }

xcmCommsOptionPreviousIndex OBJECT-TYPE
    SYNTAX      Cardinal32
    MAX-ACCESS  read-only
    STATUS      current
    DESCRIPTION
        "The value of 'xcmCommsOptionIndex' corresponding to a previous
        associated conceptual row in the 'xcmCommsOptionTable', or zero
        if this is the first associated conceptual row in a given set.

        Usage:  This object provides common 'backward' linkage for BOTH
        the 'xcmCommsOptionNextIndex' and 'xcmCommsOptionFamilyIndex'
        linkage objects.  A previous conceptual row MAY 'forward'
        reference this conceptual row via either '...NextIndex' or
        '...FamilyIndex' - ie, a given conceptual row MAY 'forward'
        reference EXACTLY zero, one, or two 'later' conceptual rows."
    REFERENCE
        "See:   'xcmCommsOption[Next|Family]Index'"
    DEFVAL      { 0 }                   -- no entry
    ::= { xcmCommsOptionEntry 11 }

xcmCommsOptionFamilyIndex OBJECT-TYPE
    SYNTAX      Cardinal32
    MAX-ACCESS  read-only
    STATUS      current
    DESCRIPTION
        "The value of 'xcmCommsOptionIndex' corresponding to the next
        'family' conceptual row in the 'xcmCommsOptionTable', or zero
        if this is the last associated conceptual row in a particular
        horizontal 'shelf' (of 'family' members) within a given set.

        Usage:  Generally, communications options (of similar or unlike
        type) are 'chained' vertically via '...[Next|Previous]Index'.
        But, in the case where particular communications options MUST
        be 'tightly coupled', they should be 'shelved' horizontally via
        '...[Family|Previous]Index' (eg, an IP address and an IP subnet
        mask)."
    REFERENCE
        "See:   'xcmCommsOption[Next|Previous]Index'"
    DEFVAL      { 0 }                   -- no entry
    ::= { xcmCommsOptionEntry 12 }


--
--          Comms Config MIB Conformance Information
--
--          With Mandatory and Optional Conformance Groups

xcmCommsConfigMIBConformance
    OBJECT IDENTIFIER ::= { xcmCommsConfigMIB 2 }
xcmCommsConfigMIBGroups
    OBJECT IDENTIFIER ::= { xcmCommsConfigMIBConformance 2 }

--
--          Compliance Statements
--

xcmCommsConfigMIBCompliance MODULE-COMPLIANCE
    STATUS      current
    DESCRIPTION
        "The compliance statements for SNMP management agents that
        implement the Comms Config MIB."
    MODULE -- this module
    MANDATORY-GROUPS {
        xcmCommsConfigGroup,
        xcmCommsOptionGroup
    }

    OBJECT      xcmCommsConfigRowStatus
    SYNTAX      INTEGER { active(1) }   -- subset of RowStatus
    DESCRIPTION
        "It is conformant to implement this object as read-only, and
        only one of the enumerated values for the 'RowStatus' textual
        convention need be supported, specifically:  active(1)."

    OBJECT      xcmCommsOptionRowStatus
    SYNTAX      INTEGER { active(1) }   -- subset of RowStatus
    DESCRIPTION
        "It is conformant to implement this object as read-only, and
        only one of the enumerated values for the 'RowStatus' textual
        convention need be supported, specifically:  active(1)."

    OBJECT      xcmCommsOptionValueString
    SYNTAX      OCTET STRING (SIZE (0..32))
    DESCRIPTION
        "It is conformant to implement this object as read-only, and
        only 32 octets maximum string length need be supported."

    ::= { xcmCommsConfigMIBConformance 3 }

--
--          Conformance Groups
--

xcmCommsConfigGroup OBJECT-GROUP
    OBJECTS {
        --  Comms Config Information


        xcmCommsConfigRowStatus,
        xcmCommsConfigActiveOptionFirst,
        xcmCommsConfigActiveOptionLast,
        xcmCommsConfigGroupSupport,
        xcmCommsConfigCreateSupport,
        xcmCommsConfigUpdateSupport
    }
    STATUS      current
    DESCRIPTION
        "Comms Config Group (Comms Configurations)."
    ::= { xcmCommsConfigMIBGroups 3 }

xcmCommsOptionGroup OBJECT-GROUP
    OBJECTS {
        --  Comms Option Information
        xcmCommsOptionRowStatus,
        xcmCommsOptionTypeOID,
        xcmCommsOptionValueSyntax,
        xcmCommsOptionValueInteger,
        xcmCommsOptionValueOID,
        xcmCommsOptionValueString,
        xcmCommsOptionValueLocalization,
        xcmCommsOptionValueCodedCharSet,
        --  Comms Option Common Cross References
        xcmCommsOptionNextIndex,
        xcmCommsOptionPreviousIndex,
        xcmCommsOptionFamilyIndex
    }
    STATUS      current
    DESCRIPTION
        "Comms Option Group (Comms Configuration Options)."
    ::= { xcmCommsConfigMIBGroups 4 }

END
