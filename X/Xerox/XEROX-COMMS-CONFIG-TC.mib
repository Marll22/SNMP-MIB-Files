XEROX-COMMS-CONFIG-TC DEFINITIONS ::= BEGIN

--  Module: Communications Configuration TC
--  Author: Ira McDonald, Alan Sullivan, Robert Westfall
--  File:   52conftc.mib
--  Date:   14 December 1997 - Version 2.40.pub

--  Textual Conventions companion to the Comms Config MIB
--  Contains the REGISTRY of XCMI Standard NetBIOS Listen Ports

IMPORTS
    MODULE-IDENTITY, OBJECT-IDENTITY,
        OBJECT-TYPE
            FROM SNMPv2-SMI             -- IETF RFC 1442/1902
    TEXTUAL-CONVENTION
            FROM SNMPv2-TC              -- IETF RFC 1443/1903
    xeroxCommonMIB
            FROM XEROX-COMMON-MIB;

xcmCommsConfigTC MODULE-IDENTITY
    LAST-UPDATED "9712140000Z"
    ORGANIZATION "Xerox Corporation - XCMI Working Group"
    CONTACT-INFO
        "           XCMI Editors
        Email:      xcmieditors@cp10.es.xerox.com

        --
        --
        "
    DESCRIPTION
        "Version:   2.40.pub

        The TC module for textual conventions, enumerated types, OIDs,
        and other volatile elements of the companion Communications
        Config MIB, which supports active configuration discovery of
        communications end system applications, communications
        intermediate systems, and communications gateways for network
        accessible host systems.

        Copyright (C) 1997 Xerox Corporation. All Rights Reserved."
    ::= { xeroxCommonMIB 63 }

--
--          The Comms Config TC
--
--          Textual Conventions

--
--          SNMP over NetBIOS Transport Domain and Transport Address
--
--          For use with SNMPv1/v2 protocols over the NetBIOS.
--
--          See section 2.0 'Definitions' of SNMPv2 Transport Mappings
--          (RFC 1449/1906) for information on SNMP mappings over other
--          network/transport protocols from other protocol suites.

xcmSnmpNetbiosDomain OBJECT-IDENTITY
    STATUS      current
    DESCRIPTION
        "The SNMP over NetBIOS transport domain.  The corresponding
        transport address is of type 'XcmSnmpNetbiosAddress'."
    ::= { xcmCommsConfigTC 3 }

XcmSnmpNetbiosAddress ::= TEXTUAL-CONVENTION
    STATUS      current
    DESCRIPTION
        "The canonical NetBIOS transport address.  The corresponding
        SNMP over NetBIOS transport domain is 'xcmSnmpNetbiosDomain'.

        The canonical NetBIOS transport address
        (registered as a NetBIOS session layer name via 'AddName'):

            Octets      Contents        Encoding
            ------      --------        --------
              1-12      MAC-address     ASCII hexadecimal (uppercase)
                        [IEEE 802.x]        ('0'-'9', 'A'-'F')
             13-14      XCMI-reserved   ASCII decimal zeros
                        [XCMI future]       ('0' - 0x30)
             15-16      NetBIOS-port    binary network-byte order


                        [XCMI std port]     (high-order byte first)
        "
    SYNTAX  OCTET STRING (SIZE (16))

--
--          REGISTRY of XCMI Standard NetBIOS Ports
--          (used with XCMI standard SNMP over NetBIOS mapping)
--
--          Entity                      Listen Port
--          ------                      -----------
--          SNMP management agent       161 (decimal)
--          SNMP management station     162 (decimal)

--
--          Comms Options Types and Syntaxes
--
--          Implementation of these options is optional for all systems,
--          and useful for ones which implement stack layer graphing
--          (via the Stack and Mux Groups) and ALSO for ones which do
--          NOT implement stack layer graphing (eg, low cost systems).

XcmCommsConfigGroupSupport ::= TEXTUAL-CONVENTION
    STATUS      current
    DESCRIPTION
        "The terse conformance statement of ALL mandatory, conditionally
        mandatory, and optional XCMI Comms Config MIB object groups
        supported by this management agent implementation (ie, version)
        on this host system, specified in a bit-mask.

        The current set of values (which may be extended in the future)
        is given below:

              1 : commsConfigGroup            -- 2**0
              2 : commsOptionGroup            -- 2**1

        Usage:  Conforming management agents shall ALWAYS accurately
        report their support for XCMI Comms Config MIB object groups."
    SYNTAX      INTEGER (0..2147483647)  -- biggest int = 2**31-1

--
--          Special Comms Option Types
--

xcmCOSpecialTypes OBJECT-IDENTITY
    STATUS      current
    DESCRIPTION
        "The root of all special comms option types defined in
        the Comms Config TC."
    ::= { xcmCommsConfigTC 4 }

xcmCOSpecialLabel OBJECT-IDENTITY
--  SYNTAX      stringDisplay
    STATUS      current
    DESCRIPTION


        "Human-readable name for the following configuration subtree,
        specified in 'xcmCommsOptionsValueString'.

        Usage:  To label tree vertices (eg, for client GUI)."
    ::= { xcmCOSpecialTypes 1 }

xcmCOSpecialImport OBJECT-IDENTITY
--  SYNTAX      integerIndex
    STATUS      current
    DESCRIPTION
        "The 'xcmCommsOptionIndex' of an 'imported' configuration
        subtree, specified in 'xcmCommsOptionValueInteger'.

        Usage:  To import a section of common config from elsewhere.
        All comms configuration options in the 'imported' subtree shall
        be 'imported' and THEN any dependent options found via the
        current 'xcmCommsOptionFamilyIndex' chain shall be treated as
        though they logically 'followed' the 'imported' configuration
        subtree.

        Usage:  This row shall be logically 're-typed' by inheritance
        from the first imported row (eg, 'xcmCOOsilanEthernet'), but
        ONLY for the 'scoping' of dependent options which are found via
        the current 'xcmCommsOptionFamilyIndex' chain (eg, a dependent
        option for 'xcmCOOsilanEthernetFrameOverride').

        Usage:  The pointer specified in 'xcmCommsOptionValueInteger'
        shall be used to evaluate the 'imported' configuration substree
        and THEN any 'local' options shall be evaluated from the current
        'xcmCommsOptionFamilyIndex' chain.

        Usage:  As would normally be true of any option, this row shall
        NOT affect the 'scoping' of independent options found via the
        current 'xcmCommsOptionNextIndex' chain (eg, the next protocol
        within a given protocol suite configuration subtree)."
    ::= { xcmCOSpecialTypes 2 }

xcmCOSpecialRemark OBJECT-IDENTITY
--  SYNTAX      stringDisplay
    STATUS      current
    DESCRIPTION
        "Human-readable remark for the following configuration subtree,
        specified in 'xcmCommsOptionsValueString'.

        Usage:  To comment tree vertices (eg, for client GUI)."
    ::= { xcmCOSpecialTypes 3 }

xcmCOSpecialAddress OBJECT-IDENTITY
--  SYNTAX      stringDisplay
    STATUS      current
    DESCRIPTION
        "Human-readable canonical address for the protocol specified in
        'xcmCommsOptionValueOID' (eg, 'xcmCOInternetIP') is specified
        in 'xcmCommsOptionsValueString' (eg, '19.242.128.21').


        Usage:  'Overloads' protocol types to yield protocol addresses."
    ::= { xcmCOSpecialTypes 4 }

--
--          OSI LAN Protocol Suite
--

xcmCOOsilanSuite
    OBJECT IDENTIFIER ::= { xcmCommsConfigTC 11 }
    -- integerTruthValue

xcmCOOsilanPhysicals
    OBJECT IDENTIFIER ::= { xcmCOOsilanSuite 1100 }
    -- integerTruthValue
xcmCOOsilanConnectorType        -- OSI LAN Connector Type
    OBJECT IDENTIFIER ::= { xcmCOOsilanPhysicals 1 }
    -- integerEnum (1=none, 2=other, 3=rj11, 4=rj45, 5=db9,
    -- 6=bnc, 7=aui, 8=sma, 9=rg48)
xcmCOOsilanConnectorOverride    -- OSI LAN Connector Type Override
    OBJECT IDENTIFIER ::= { xcmCOOsilanConnectorType 1 }
    -- integerEnum (1=none, 2=other, 3=rj11, 4=rj45, 5=db9,
    -- 6=bnc, 7=aui, 8=sma, 9=rg48)
xcmCOOsilanSignalType           -- OSI LAN Signal Type
    OBJECT IDENTIFIER ::= { xcmCOOsilanPhysicals 2 }
    -- integerEnum (1=none, 2=other,
    -- 3=10baseT, 4=10base2, 5=10base5, 6=10baseFL, - Standard Ethernet
    -- 7=100baseTX, 8=100baseFX,                    - Fast Ethernet
    -- 9=4mbTokenRing, 10=16mbTokenRing)            - Token Ring
xcmCOOsilanCableType            -- OSI LAN Cable Type
    OBJECT IDENTIFIER ::= { xcmCOOsilanPhysicals 3 }
    -- integerEnum (1=none, 2=other,
    -- 3=utp, 4=stp, 5=ftp,                         - Twisted Pair
    -- 6=thinCoax, 7=thickCoax,                     - Coax
    -- 8=fiber)                                     - Fiber

xcmCOOsilanDatalinks
    OBJECT IDENTIFIER ::= { xcmCOOsilanSuite 1200 }
    -- integerTruthValue (w/ chain of 'xcmCOOsilan...')
xcmCOOsilanFrameType            -- OSI LAN Frame Type
    OBJECT IDENTIFIER ::= { xcmCOOsilanSuite 1201 }
    -- integerEnum (1=llc, 2=snap, 3=mac, 4=ethernetII, 5=adaptive)
    -- (Ethernet [IEEE 802.3] supports all five of above frame types)
    -- (ALL others [IEEE 802.x] support ONLY llc, snap, or adaptive)
xcmCOOsilanFrameOverride        -- OSI LAN Frame Type Override
    OBJECT IDENTIFIER ::= { xcmCOOsilanFrameType 1 }
    -- integerEnum (1=llc, 2=snap, 3=mac, 4=ethernetII, 5=adaptive)
xcmCOOsilanEthernet             -- OSI LAN Ethernet (IEEE 802.3)
    OBJECT IDENTIFIER ::= { xcmCOOsilanSuite 1203 }
    -- integerTruthValue
xcmCOOsilanTokenBus             -- OSI LAN Token Bus (IEEE 802.4)
    OBJECT IDENTIFIER ::= { xcmCOOsilanSuite 1204 }
    -- integerTruthValue
xcmCOOsilanTokenRing            -- OSI LAN Token Ring (IEEE 802.5)


    OBJECT IDENTIFIER ::= { xcmCOOsilanSuite 1205 }
    -- integerTruthValue
xcmCOOsilanFDDI                 -- OSI LAN FDDI
    OBJECT IDENTIFIER ::= { xcmCOOsilanSuite 1207 }
    -- integerTruthValue

xcmCOOsilanEthernetType
    OBJECT IDENTIFIER ::= { xcmCOOsilanEthernet 1 }
    -- integerEnum (...need enum)
xcmCOOsilanEthernetDevice
    OBJECT IDENTIFIER ::= { xcmCOOsilanEthernet 2 }
    -- integerNumber ('hrDeviceIndex' in IETF HR MIB, or 0=unknown)
xcmCOOsilanEthernetDeviceName
    OBJECT IDENTIFIER ::= { xcmCOOsilanEthernetDevice 1 }
    -- stringDisplay ('xcmHrDevInfoName' in HRX MIB, eg, '/dev/elan1')
xcmCOOsilanEthernetSpeed
    OBJECT IDENTIFIER ::= { xcmCOOsilanEthernet 3 }
    -- integerNumber (as in 'ifSpeed' in IETF MIB-II)

xcmCOOsilanTokenRingType
    OBJECT IDENTIFIER ::= { xcmCOOsilanTokenRing 1 }
    -- integerEnum (...need enum)
xcmCOOsilanTokenRingDevice
    OBJECT IDENTIFIER ::= { xcmCOOsilanTokenRing 2 }
    -- integerNumber ('hrDeviceIndex' in IETF HR MIB, or 0=unknown)
xcmCOOsilanTokenRingDeviceName
    OBJECT IDENTIFIER ::= { xcmCOOsilanTokenRingDevice 1 }
    -- stringDisplay ('xcmHrDevInfoName' in HRX MIB, eg, '/dev/trlan1')
xcmCOOsilanTokenRingSpeed
    OBJECT IDENTIFIER ::= { xcmCOOsilanTokenRing 3 }
    -- integerNumber (as in 'ifSpeed' in IETF MIB-II)
xcmCOOsilanTokenRingSSR         -- OSI LAN Token Ring Source Stn Route
    OBJECT IDENTIFIER ::= { xcmCOOsilanTokenRing 11 }
    -- integerTruthValue (true=enableSSR, false=disableSSR)

--
--          OSI WAN Protocol Suite
--

xcmCOOsiwanSuite
    OBJECT IDENTIFIER ::= { xcmCommsConfigTC 13 }
    -- integerTruthValue

xcmCOOsiwanPhysicals
    OBJECT IDENTIFIER ::= { xcmCOOsiwanSuite 1100 }
    -- integerTruthValue

xcmCOOsiwanDatalinks
    OBJECT IDENTIFIER ::= { xcmCOOsiwanSuite 1200 }
    -- integerTruthValue (w/ chain of 'xcmCOOsiwan...')
xcmCOOsiwanFax                  -- CCITT Fax (facsimile)
    OBJECT IDENTIFIER ::= { xcmCOOsiwanSuite 1241 }
    -- integerTruthValue
xcmCOOsiwanPSTN                 -- CCITT PSTN (analog telephone)


    OBJECT IDENTIFIER ::= { xcmCOOsiwanSuite 1251 }
    -- integerTruthValue
xcmCOOsiwanISDN                 -- CCITT ISDN (digital telephone)
    OBJECT IDENTIFIER ::= { xcmCOOsiwanSuite 1261 }
    -- integerTruthValue

xcmCOOsiwanFaxAddress           -- CCITT Fax (facsimile)
    OBJECT IDENTIFIER ::= { xcmCOOsiwanFax 1 }
    -- stringDisplay
xcmCOOsiwanPSTNAddress          -- CCITT PSTN (analog telephone)
    OBJECT IDENTIFIER ::= { xcmCOOsiwanPSTN 1 }
    -- stringDisplay
xcmCOOsiwanISDNAddress          -- CCITT ISDN (digital telephone)
    OBJECT IDENTIFIER ::= { xcmCOOsiwanISDN 1 }
    -- stringDisplay

xcmCOOsiwanTransports
    OBJECT IDENTIFIER ::= { xcmCOOsiwanSuite 1400 }
    -- integerTruthValue

xcmCOOsiwanApplications
    OBJECT IDENTIFIER ::= { xcmCOOsiwanSuite 1700 }
    -- integerTruthValue
xcmCOOsiwanDPA                          -- ISO 10175 (printing)
    OBJECT IDENTIFIER ::= { xcmCOOsiwanSuite 1713 }
    -- integerTruthValue
xcmCOOsiwanFTAM                         -- ISO 8571 (filing)
    OBJECT IDENTIFIER ::= { xcmCOOsiwanSuite 1714 }
    -- integerTruthValue
xcmCOOsiwanVT                           -- ISO 9041 (terminal)
    OBJECT IDENTIFIER ::= { xcmCOOsiwanSuite 1716 }
    -- integerTruthValue
xcmCOOsiwanMHS                          -- CCITT X.400 (email)
    OBJECT IDENTIFIER ::= { xcmCOOsiwanSuite 1740 }
    -- integerTruthValue
xcmCOOsiwanDS                           -- CCITT X.500 (directory)
    OBJECT IDENTIFIER ::= { xcmCOOsiwanSuite 1750 }
    -- integerTruthValue
xcmCOOsiwanDAP                          -- CCITT X.500 DAP (access)
    OBJECT IDENTIFIER ::= { xcmCOOsiwanSuite 1751 }
    -- integerTruthValue
xcmCOOsiwanDSP                          -- CCITT X.500 DSP (backbones)
    OBJECT IDENTIFIER ::= { xcmCOOsiwanSuite 1752 }
    -- integerTruthValue
xcmCOOsiwanMgmt                         -- CCITT X.700 (system mgmt)
    OBJECT IDENTIFIER ::= { xcmCOOsiwanSuite 1770 }
    -- integerTruthValue
xcmCOOsiwanCMIP                         -- CCITT X.710/X.711 CMIP (mgmt)
    OBJECT IDENTIFIER ::= { xcmCOOsiwanSuite 1771 }
    -- integerTruthValue
xcmCOOsiwanSecurity                     -- CCITT X.800 (system security)
    OBJECT IDENTIFIER ::= { xcmCOOsiwanSuite 1780 }
    -- integerTruthValue


--
--          Internet Protocol Suite
--

xcmCOInternetSuite
    OBJECT IDENTIFIER ::= { xcmCommsConfigTC 14 }
    -- integerTruthValue

xcmCOInternetDatalinks
    OBJECT IDENTIFIER ::= { xcmCOInternetSuite 1200 }
    -- integerTruthValue (w/ chain of 'xcmCOOsilan...')
xcmCOInternetSLIP               -- SLIP (serial datalink)
    OBJECT IDENTIFIER ::= { xcmCOInternetSuite 1201 }
    -- integerTruthValue
xcmCOInternetPPP                -- PPP (serial datalink)
    OBJECT IDENTIFIER ::= { xcmCOInternetSuite 1202 }
    -- integerTruthValue

xcmCOInternetTransports
    OBJECT IDENTIFIER ::= { xcmCOInternetSuite 1400 }
    -- integerTruthValue
xcmCOInternetIP                 -- IP (CL network)
    OBJECT IDENTIFIER ::= { xcmCOInternetSuite 1301 }
    -- integerTruthValue
xcmCOInternetICMP               -- ICMP (layer management - network)
    OBJECT IDENTIFIER ::= { xcmCOInternetSuite 1302 }
    -- integerTruthValue
xcmCOInternetARP                -- ARP (routing)
    OBJECT IDENTIFIER ::= { xcmCOInternetSuite 1303 }
    -- integerTruthValue
xcmCOInternetDHCP               -- DHCP (routing/boot)
    OBJECT IDENTIFIER ::= { xcmCOInternetSuite 1304 }
    -- integerTruthValue
xcmCOInternetBOOTP              -- BOOTP (routing/boot)
    OBJECT IDENTIFIER ::= { xcmCOInternetSuite 1305 }
    -- integerTruthValue
xcmCOInternetRARP               -- RARP (routing/boot)
    OBJECT IDENTIFIER ::= { xcmCOInternetSuite 1306 }
    -- integerTruthValue
xcmCOInternetUDP                -- UDP (CL transport)
    OBJECT IDENTIFIER ::= { xcmCOInternetSuite 1401 }
    -- integerTruthValue
xcmCOInternetTCP                -- TCP (CO transport)
    OBJECT IDENTIFIER ::= { xcmCOInternetSuite 1402 }
    -- integerTruthValue
xcmCOInternetPing               -- Ping (echo)
    OBJECT IDENTIFIER ::= { xcmCOInternetSuite 1404 }
    -- integerTruthValue

xcmCOInternetIPAddress          -- IP Node Address
    OBJECT IDENTIFIER ::= { xcmCOInternetIP 1 }
    -- stringDisplay (dotted decimal format, 'a.b.c.d')
    -- ('a' to 'd' [1-3 octets] - ASCII decimal of 1-octet components)


xcmCOInternetIPSocketAddress    -- IP Socket Address
    OBJECT IDENTIFIER ::= { xcmCOInternetIPAddress 1 }
    -- stringDisplay (dotted decimal format, 'a.b.c.d.socket')
    -- ('a' to 'd' [1-3 octets] - ASCII decimal of 1-octet components)
    -- ('socket' [1-5 octets] - ASCII decimal of 2-octet socket)
xcmCOInternetIPSubnetMask       -- IP Subnet Mask
    OBJECT IDENTIFIER ::= { xcmCOInternetIP 2 }
    -- stringDisplay (dotted decimal format, NOT internal hex)
xcmCOInternetIPAddressViaRARP   -- IP Address Via RARP (dynamic)
    OBJECT IDENTIFIER ::= { xcmCOInternetIP 3 }
    -- integerTruthValue (true=enableRARP, false=disableRARP)
    -- (if false, then use 'xcmCOInternetIPAddress' value)
    -- (obsoleted by 'xcmCOInternetIPAddressSource')
xcmCOInternetIPDefaultGateway   -- IP Default Gateway
    OBJECT IDENTIFIER ::= { xcmCOInternetIP 4 }
    -- stringDisplay (dotted decimal format, NOT internal hex)
xcmCOInternetIPAddressSource    -- IP Address Source (static/dynamic)
    OBJECT IDENTIFIER ::= { xcmCOInternetIP 5 }
    -- integerEnum (1=none, 2=other,
    -- 3=static, 4=viaRARP, 5=viaBOOTP, 6=viaDHCP)
    -- (obsoletes 'xcmCOInternetIPAddressViaRARP')
xcmCOInternetIPDatalinks        -- IP Datalinks
    OBJECT IDENTIFIER ::= { xcmCOInternetIP 12 }
    -- integerTruthValue (w/ chain of 'xcmCOOsilan...')

xcmCOInternetDHCPClassID        -- DHCP Class ID (option to server)
    OBJECT IDENTIFIER ::= { xcmCOInternetDHCP 1 }
    -- stringBinary
xcmCOInternetDHCPLeaseTime      -- DHCP Lease Time (option to server)
    OBJECT IDENTIFIER ::= { xcmCOInternetDHCP 2 }
    -- integerNumber (seconds, 0=none, or 1..n)

xcmCOInternetUDPAddress         -- UDP Address
    OBJECT IDENTIFIER ::= { xcmCOInternetUDP 1 }
    -- stringDisplay (dotted decimal format, 'a.b.c.d.socket')
xcmCOInternetUDPPort            -- UDP Port
    OBJECT IDENTIFIER ::= { xcmCOInternetUDP 2 }
    -- stringDisplay (ASCII decimal format, 'socket')

xcmCOInternetTCPAddress         -- TCP Address
    OBJECT IDENTIFIER ::= { xcmCOInternetTCP 1 }
    -- stringDisplay (dotted decimal format, 'a.b.c.d.socket')
xcmCOInternetTCPPort            -- TCP Port
    OBJECT IDENTIFIER ::= { xcmCOInternetTCP 2 }
    -- stringDisplay (ASCII decimal format, 'socket')

xcmCOInternetApplications
    OBJECT IDENTIFIER ::= { xcmCOInternetSuite 1700 }
    -- integerTruthValue
xcmCOInternetLPR                -- LPR (printing)
    OBJECT IDENTIFIER ::= { xcmCOInternetSuite 1503 }
    -- integerTruthValue
xcmCOInternetFTP                -- FTP (filing)
    OBJECT IDENTIFIER ::= { xcmCOInternetSuite 1504 }


    -- integerTruthValue
xcmCOInternetSMTP               -- SMTP (email)
    OBJECT IDENTIFIER ::= { xcmCOInternetSuite 1505 }
    -- integerTruthValue
xcmCOInternetTelnet             -- Telnet (virtual terminal)
    OBJECT IDENTIFIER ::= { xcmCOInternetSuite 1506 }
    -- integerTruthValue
xcmCOInternetDNS                -- DNS (directory)
    OBJECT IDENTIFIER ::= { xcmCOInternetSuite 1507 }
    -- integerTruthValue
xcmCOInternetTFTP               -- TFTP (filing)
    OBJECT IDENTIFIER ::= { xcmCOInternetSuite 1508 }
    -- integerTruthValue
xcmCOInternetHTTP               -- HTTP (World Wide Web)
    OBJECT IDENTIFIER ::= { xcmCOInternetSuite 1509 }
    -- integerTruthValue

xcmCOInternetSNMP               -- SNMP (network mgmt)
    OBJECT IDENTIFIER ::= { xcmCOInternetSuite 1510 }
    -- integerTruthValue
xcmCOInternetSNMPv1             -- SNMPv1 (network mgmt)
    OBJECT IDENTIFIER ::= { xcmCOInternetSuite 1511 }
    -- integerTruthValue
    -- (obsoleted by 'xcmCOInternetSNMPVersion')
xcmCOInternetSNMPv2             -- SNMPv2 (network mgmt)
    OBJECT IDENTIFIER ::= { xcmCOInternetSuite 1512 }
    -- integerTruthValue
    -- (obsoleted by 'xcmCOInternetSNMPVersion')
xcmCOInternetSNMPVersion        -- SNMP Version (network mgmt)
    OBJECT IDENTIFIER ::= { xcmCOInternetSNMP 1 }
    -- integerEnum (from 'XcmGenSNMPVersion' in XCMI General TC)
    -- (obsoletes 'xcmCOInternetSNMP[v1|v2]')

xcmCOInternetSunOncSuite        -- Sun ONC Suite (distributed computing)
    OBJECT IDENTIFIER ::= { xcmCOInternetSuite 1520 }
    -- integerTruthValue
xcmCOInternetSunOncNIS          -- Sun ONC NIS (directory)
    OBJECT IDENTIFIER ::= { xcmCOInternetSuite 1521 }
    -- integerTruthValue
xcmCOInternetSunOncPlusNIS      -- Sun ONC+ NIS+ (directory)
    OBJECT IDENTIFIER ::= { xcmCOInternetSuite 1522 }
    -- integerTruthValue
xcmCOInternetSunOncRPC          -- Sun ONC RPC (w/ NIS)
    OBJECT IDENTIFIER ::= { xcmCOInternetSuite 1523 }
    -- integerTruthValue
xcmCOInternetSunOncPlusRPC      -- Sun ONC+ RPC (w/ NIS+)
    OBJECT IDENTIFIER ::= { xcmCOInternetSuite 1524 }
    -- integerTruthValue
xcmCOInternetSunTiRPC           -- Sun TI RPC (transactions)
    OBJECT IDENTIFIER ::= { xcmCOInternetSuite 1525 }
    -- integerTruthValue

xcmCOInternetOsfDceSuite        -- OSF DCE Suite (distributed computing)
    OBJECT IDENTIFIER ::= { xcmCOInternetSuite 1530 }


    -- integerTruthValue
xcmCOInternetOsfDceCDS          -- OSF DCE CDS (directory)
    OBJECT IDENTIFIER ::= { xcmCOInternetSuite 1531 }
    -- integerTruthValue
xcmCOInternetOsfDceRPC          -- OSF DCE RPC (w/ CDS)
    OBJECT IDENTIFIER ::= { xcmCOInternetSuite 1532 }
    -- integerTruthValue
xcmCOInternetOsfDceKerberos     -- OSF DCE Kerberos (security tickets)
    OBJECT IDENTIFIER ::= { xcmCOInternetSuite 1533 }
    -- integerTruthValue

xcmCOInternetOsfDmeSuite        -- OSF DME Suite (distributed mgmt)
    OBJECT IDENTIFIER ::= { xcmCOInternetSuite 1540 }
    -- integerTruthValue

xcmCOInternetLDAP               -- LDAP (to X.500 directory, RFC 1777)
    OBJECT IDENTIFIER ::= { xcmCOInternetSuite 1551 }
    -- integerTruthValue
xcmCOInternetCLDAP              -- CLDAP (to X.500 directory, RFC 1798)
    OBJECT IDENTIFIER ::= { xcmCOInternetSuite 1552 }
    -- integerTruthValue

xcmCOInternetLPRHostName        -- LPR Host Name
    OBJECT IDENTIFIER ::= { xcmCOInternetLPR 1 }
    -- stringDisplay
xcmCOInternetLPRHostAddress     -- LPR Host Address
    OBJECT IDENTIFIER ::= { xcmCOInternetLPR 2 }
    -- stringDisplay (dotted decimal format, NOT internal hex)
xcmCOInternetLPRListenSocket    -- LPR Listen Socket (RFC 1179)
    OBJECT IDENTIFIER ::= { xcmCOInternetLPR 3 }
    -- integerNumber (515=default or 1..n)
xcmCOInternetLPRMaxClients      -- LPR Max Clients (concurrently)
    OBJECT IDENTIFIER ::= { xcmCOInternetLPR 4 }
    -- integerNumber (0..n)
xcmCOInternetLPRAcceptAddress   -- LPR Accept Address (list)
    OBJECT IDENTIFIER ::= { xcmCOInternetLPR 11 }
    -- integerTruthValue (w/ chain of 'xcmCOInternetIPAddress')
xcmCOInternetLPRAcceptSubnet    -- LPR Accept Subnet (list)
    OBJECT IDENTIFIER ::= { xcmCOInternetLPR 12 }
    -- integerTruthValue (w/ chain of 'xcmCOInternetIPSubnetMask')
xcmCOInternetLPRRejectAddress   -- LPR Reject Address (list)
    OBJECT IDENTIFIER ::= { xcmCOInternetLPR 21 }
    -- integerTruthValue (w/ chain of 'xcmCOInternetIPAddress')
xcmCOInternetLPRRejectSubnet    -- LPR Reject Subnet (list)
    OBJECT IDENTIFIER ::= { xcmCOInternetLPR 22 }
    -- integerTruthValue (w/ chain of 'xcmCOInternetIPSubnetMask')
xcmCOInternetLPRSpool           -- LPR Spool (print spooling)
    OBJECT IDENTIFIER ::= { xcmCOInternetLPR 31 }
    -- integerEnum (1=none, 2=other, 3=disk, 4=ram)
xcmCOInternetLPRMaxSpool        -- LPR Max Spool (print spooling)
    OBJECT IDENTIFIER ::= { xcmCOInternetLPR 32 }
    -- integerNumber (spool area size in bytes, 0..n)


--
--          AppleTalk Protocol Suite
--

xcmCOAppletalkSuite
    OBJECT IDENTIFIER ::= { xcmCommsConfigTC 18 }
    -- integerTruthValue

xcmCOAppletalkDatalinks
    OBJECT IDENTIFIER ::= { xcmCOAppletalkSuite 1200 }
    -- integerTruthValue (w/ chain of 'xcmCOOsilan...')
xcmCOAppletalkLLAP              -- LocalTalk LAP (datalink)
    OBJECT IDENTIFIER ::= { xcmCOAppletalkSuite 1201 }
    -- integerTruthValue
xcmCOAppletalkELAP              -- EtherTalk LAP (datalink)
    OBJECT IDENTIFIER ::= { xcmCOAppletalkSuite 1202 }
    -- integerTruthValue
xcmCOAppletalkTLAP              -- TokenTalk LAP (datalink)
    OBJECT IDENTIFIER ::= { xcmCOAppletalkSuite 1203 }
    -- integerTruthValue
xcmCOAppletalkPhase             -- AppleTalk Phase (datalink)
    OBJECT IDENTIFIER ::= { xcmCOAppletalkSuite 1211 }
    -- integerEnum (1=phase1, 2=phase2)

xcmCOAppletalkTransports
    OBJECT IDENTIFIER ::= { xcmCOAppletalkSuite 1400 }
    -- integerTruthValue
xcmCOAppletalkDDP               -- DDP (CL network)
    OBJECT IDENTIFIER ::= { xcmCOAppletalkSuite 1301 }
    -- integerTruthValue
xcmCOAppletalkAARP              -- AARP (routing)
    OBJECT IDENTIFIER ::= { xcmCOAppletalkSuite 1303 }
    -- integerTruthValue
xcmCOAppletalkADP               -- ADP (CL transport)
    OBJECT IDENTIFIER ::= { xcmCOAppletalkSuite 1401 }
    -- integerTruthValue
xcmCOAppletalkADSP              -- ADSP (CO transport)
    OBJECT IDENTIFIER ::= { xcmCOAppletalkSuite 1402 }
    -- integerTruthValue
xcmCOAppletalkRTMP              -- RTMP (routing)
    OBJECT IDENTIFIER ::= { xcmCOAppletalkSuite 1403 }
    -- integerTruthValue
xcmCOAppletalkAEP               -- AEP (echo)
    OBJECT IDENTIFIER ::= { xcmCOAppletalkSuite 1404 }
    -- integerTruthValue
xcmCOAppletalkNBP               -- NBP (directory)
    OBJECT IDENTIFIER ::= { xcmCOAppletalkSuite 1405 }
    -- integerTruthValue

xcmCOAppletalkDDPAddress        -- DDP Node Address
    OBJECT IDENTIFIER ::= { xcmCOAppletalkDDP 1 }
    -- stringDisplay (dotted ASCII hex format, 'network.node')
    -- ('network' [4 octets] - ASCII hex of 2-octet AppleTalk network)
    -- ('node'    [2 octets] - ASCII hex of 1-octet AppleTalk node)


xcmCOAppletalkDDPSocketAddress  -- DDP Socket Address
    OBJECT IDENTIFIER ::= { xcmCOAppletalkDDPAddress 1 }
    -- stringDisplay (dotted ASCII hex format, 'network.node.socket')
    -- ('network' [4 octets] - ASCII hex of 2-octet AppleTalk network)
    -- ('node'    [2 octets] - ASCII hex of 1-octet AppleTalk node)
    -- ('socket'  [2 octets] - ASCII hex of 1-octet AppleTalk socket)
xcmCOAppletalkDDPDatalinks      -- DDP Datalinks
    OBJECT IDENTIFIER ::= { xcmCOAppletalkDDP 12 }
    -- integerTruthValue (w/ chain of 'xcmCOOsilan...')

xcmCOAppletalkApplications
    OBJECT IDENTIFIER ::= { xcmCOAppletalkSuite 1700 }
    -- integerTruthValue
xcmCOAppletalkASP               -- ASP (CO session)
    OBJECT IDENTIFIER ::= { xcmCOAppletalkSuite 1501 }
    -- integerTruthValue
xcmCOAppletalkZIP               -- ZIP (directory)
    OBJECT IDENTIFIER ::= { xcmCOAppletalkSuite 1502 }
    -- integerTruthValue
xcmCOAppletalkPAP               -- PAP (printing)
    OBJECT IDENTIFIER ::= { xcmCOAppletalkSuite 1503 }
    -- integerTruthValue

xcmCOAppletalkSNMP              -- SNMP (network mgmt)
    OBJECT IDENTIFIER ::= { xcmCOAppletalkSuite 1510 }
    -- integerTruthValue
xcmCOAppletalkSNMPv1            -- SNMPv1 (network mgmt)
    OBJECT IDENTIFIER ::= { xcmCOAppletalkSuite 1511 }
    -- integerTruthValue
xcmCOAppletalkSNMPv2            -- SNMPv2 (network mgmt)
    OBJECT IDENTIFIER ::= { xcmCOAppletalkSuite 1512 }
    -- integerTruthValue

xcmCOAppletalkAFP               -- AFP (filing)
    OBJECT IDENTIFIER ::= { xcmCOAppletalkSuite 1601 }
    -- integerTruthValue
xcmCOAppletalkPS                -- PostScript (printing)
    OBJECT IDENTIFIER ::= { xcmCOAppletalkSuite 1602 }
    -- integerTruthValue

xcmCOAppletalkPAPHostName       -- PAP Host Name ('Object:Type@Zone')
    OBJECT IDENTIFIER ::= { xcmCOAppletalkPAP 1 }
    -- stringDisplay
xcmCOAppletalkPAPHostAddress    -- PAP Host Address
    OBJECT IDENTIFIER ::= { xcmCOAppletalkPAP 2 }
    -- stringDisplay (dotted ASCII hex format, 'network.node.socket')
xcmCOAppletalkPAPListenSocket   -- PAP Listen Socket
    OBJECT IDENTIFIER ::= { xcmCOAppletalkPAP 3 }
    -- integerNumber (140=default or 3..255)
xcmCOAppletalkPAPMaxClients     -- PAP Max Clients (concurrently)
    OBJECT IDENTIFIER ::= { xcmCOAppletalkPAP 4 }
    -- integerNumber (0..n)
xcmCOAppletalkPAPMaxPrinters    -- PAP Max Printers (printing)
    OBJECT IDENTIFIER ::= { xcmCOAppletalkPAP 5 }


    -- integerNumber (1=default or 1..n)
xcmCOAppletalkPAPObject         -- PAP Object (printing)
    OBJECT IDENTIFIER ::= { xcmCOAppletalkPAP 11 }
    -- stringDisplay
xcmCOAppletalkPAPType           -- PAP Type (printing)
    OBJECT IDENTIFIER ::= { xcmCOAppletalkPAP 12 }
    -- stringDisplay ('LaserWriter'=default)
xcmCOAppletalkPAPZone           -- PAP Zone (printing)
    OBJECT IDENTIFIER ::= { xcmCOAppletalkPAP 13 }
    -- stringDisplay
xcmCOAppletalkPAPNetwork        -- PAP Network (printing)
    OBJECT IDENTIFIER ::= { xcmCOAppletalkPAP 21 }
    -- integerNumber (0..65534)
xcmCOAppletalkPAPNode           -- PAP Node (printing)
    OBJECT IDENTIFIER ::= { xcmCOAppletalkPAP 22 }
    -- integerNumber (0..254)
xcmCOAppletalkPAPSpool          -- PAP Spool (print spooling)
    OBJECT IDENTIFIER ::= { xcmCOAppletalkPAP 31 }
    -- integerEnum (1=none, 2=other, 3=disk, 4=ram)
xcmCOAppletalkPAPMaxSpool       -- PAP Max Spool (print spooling)
    OBJECT IDENTIFIER ::= { xcmCOAppletalkPAP 32 }
    -- integerNumber (spool area size in bytes, 0..n)

--
--          NetWare Protocol Suite
--

xcmCONetwareSuite
    OBJECT IDENTIFIER ::= { xcmCommsConfigTC 19 }
    -- integerTruthValue

xcmCONetwareDatalinks
    OBJECT IDENTIFIER ::= { xcmCONetwareSuite 1200 }
    -- integerTruthValue (w/ chain of 'xcmCOOsilan...')

xcmCONetwareTransports
    OBJECT IDENTIFIER ::= { xcmCONetwareSuite 1400 }
    -- integerTruthValue
xcmCONetwareIPX                 -- IPX (CL network)
    OBJECT IDENTIFIER ::= { xcmCONetwareSuite 1301 }
    -- integerTruthValue
xcmCONetwareSPX                 -- SPX (CO transport)
    OBJECT IDENTIFIER ::= { xcmCONetwareSuite 1402 }
    -- integerTruthValue
xcmCONetwareRIP                 -- RIP (routing)
    OBJECT IDENTIFIER ::= { xcmCONetwareSuite 1403 }
    -- integerTruthValue
xcmCONetwareEcho                -- Echo (echo)
    OBJECT IDENTIFIER ::= { xcmCONetwareSuite 1404 }
    -- integerTruthValue

xcmCONetwareIPXAddress          -- IPX Node Address
    OBJECT IDENTIFIER ::= { xcmCONetwareIPX 1 }
    -- stringDisplay (dotted ASCII hex format, 'network.node')


    -- ('network' [8 octets] - unique network ID, '0' means 'local net')
    -- ('node'    [12 octets] - ASCII hex of IEEE 802.x MAC address)
xcmCONetwareIPXSocketAddress    -- IPX Socket Address
    OBJECT IDENTIFIER ::= { xcmCONetwareIPXAddress 1 }
    -- stringDisplay (dotted ASCII hex format, 'network.node.socket')
    -- ('network' [8 octets] - unique network ID, '0' means 'local net')
    -- ('node'    [12 octets] - ASCII hex of IEEE 802.x MAC address)
    -- ('socket'  [4 octets] - ASCII hex of 2-octet NetWare socket)
xcmCONetwareIPXDatalinks        -- IPX Datalinks
    OBJECT IDENTIFIER ::= { xcmCONetwareIPX 12 }
    -- integerTruthValue (w/ chain of 'xcmCOOsilan...')

xcmCONetwareApplications
    OBJECT IDENTIFIER ::= { xcmCONetwareSuite 1700 }
    -- integerTruthValue
xcmCONetwareNCP                 -- NCP (core protocols)
    OBJECT IDENTIFIER ::= { xcmCONetwareSuite 1501 }
    -- integerTruthValue
xcmCONetwareNetbios             -- NetBIOS Emulation
    OBJECT IDENTIFIER ::= { xcmCONetwareSuite 1502 }
    -- integerTruthValue
xcmCONetwarePServer             -- PServer (printing)
    OBJECT IDENTIFIER ::= { xcmCONetwareSuite 1503 }
    -- integerTruthValue
xcmCONetwareFServer             -- FServer (filing)
    OBJECT IDENTIFIER ::= { xcmCONetwareSuite 1504 }
    -- integerTruthValue
xcmCONetwareMHS                 -- MHS (email)
    OBJECT IDENTIFIER ::= { xcmCONetwareSuite 1505 }
    -- integerTruthValue
xcmCONetwareBindery             -- Bindery (directory)
    OBJECT IDENTIFIER ::= { xcmCONetwareSuite 1507 }
    -- integerTruthValue
xcmCONetwareNDS                 -- NDS (directory)
    OBJECT IDENTIFIER ::= { xcmCONetwareSuite 1508 }
    -- integerTruthValue
xcmCONetwareRPrinter            -- RPrinter (printing)
    OBJECT IDENTIFIER ::= { xcmCONetwareSuite 1509 }
    -- integerTruthValue

xcmCONetwareSNMP                -- SNMP (network mgmt)
    OBJECT IDENTIFIER ::= { xcmCONetwareSuite 1510 }
    -- integerTruthValue
xcmCONetwareSNMPv1              -- SNMPv1 (network mgmt)
    OBJECT IDENTIFIER ::= { xcmCONetwareSuite 1511 }
    -- integerTruthValue
xcmCONetwareSNMPv2              -- SNMPv2 (network mgmt)
    OBJECT IDENTIFIER ::= { xcmCONetwareSuite 1512 }
    -- integerTruthValue

xcmCONetwareSAP                 -- SAP (service advertise)
    OBJECT IDENTIFIER ::= { xcmCONetwareSuite 1591 }
    -- integerTruthValue


xcmCONetwarePServerName         -- PServer Name (printing)
    OBJECT IDENTIFIER ::= { xcmCONetwarePServer 1 }
    -- stringDisplay
xcmCONetwarePServerPassword     -- PServer Password (printing)
    OBJECT IDENTIFIER ::= { xcmCONetwarePServer 2 }
    -- stringDisplay (shall ALWAYS be encrypted)
xcmCONetwarePServerQueueName    -- PServer Queue Name (printing)
    OBJECT IDENTIFIER ::= { xcmCONetwarePServer 3 }
    -- stringDisplay
xcmCONetwarePServerPollInterval -- PServer Poll Interval (printing)
    OBJECT IDENTIFIER ::= { xcmCONetwarePServer 4 }
    -- integerNumber (seconds, 0=immediate or 1..n)
xcmCONetwarePServerFindFServer  -- PServer Find FServer (printing)
    OBJECT IDENTIFIER ::= { xcmCONetwarePServer 5 }
    -- integerTruthValue (true=enableFind, false=disableFind)
xcmCONetwarePServerMaxFServers  -- PServer Max FServers (printing)
    OBJECT IDENTIFIER ::= { xcmCONetwarePServer 6 }
    -- integerNumber (1..n)
xcmCONetwarePServerNotify       -- PServer Notify (printing)
    OBJECT IDENTIFIER ::= { xcmCONetwarePServer 7 }
    -- integerTruthValue (true=enableNotify, false=disableNotify)
xcmCONetwarePServerMaxPrinters  -- PServer Max Printers (printing)
    OBJECT IDENTIFIER ::= { xcmCONetwarePServer 8 }
    -- integerNumber (1=default or 1..n)
xcmCONetwarePServerSpool        -- PServer Spool (print spooling)
    OBJECT IDENTIFIER ::= { xcmCONetwarePServer 31 }
    -- integerEnum (1=none, 2=other, 3=disk, 4=ram)
xcmCONetwarePServerMaxSpool     -- PServer Max Spool (print spooling)
    OBJECT IDENTIFIER ::= { xcmCONetwarePServer 32 }
    -- integerNumber (spool area size in bytes, 0..n)

xcmCONetwareRPrinterName        -- RPrinter PServer Name (printing)
    OBJECT IDENTIFIER ::= { xcmCONetwareRPrinter 1 }
    -- stringDisplay
xcmCONetwareRPrinterNumber      -- RPrinter Printer Number (printing)
    OBJECT IDENTIFIER ::= { xcmCONetwareRPrinter 2 }
    -- integerNumber (1..n)
xcmCONetwareRPrinterPollInterval -- RPrinter Poll Interval (printing)
    OBJECT IDENTIFIER ::= { xcmCONetwareRPrinter 3 }
    -- integerNumber (seconds, 0=immediate or 1..n)

xcmCONetwareFServerName         -- FServer Name (filing)
    OBJECT IDENTIFIER ::= { xcmCONetwareFServer 1 }
    -- stringDisplay
xcmCONetwareFServerPassword     -- FServer Password (filing)
    OBJECT IDENTIFIER ::= { xcmCONetwareFServer 2 }
    -- stringDisplay (shall ALWAYS be encrypted)
xcmCONetwareFServerAddress      -- FServer Address (filing)
    OBJECT IDENTIFIER ::= { xcmCONetwareFServer 3 }
    -- stringDisplay (dotted ASCII hex format, 'network.node')

xcmCONetwareNDSTreeName         -- NDS Tree Name (directory)
    OBJECT IDENTIFIER ::= { xcmCONetwareNDS 1 }


    -- stringDisplay
xcmCONetwareNDSContext          -- NDS Context (directory)
    OBJECT IDENTIFIER ::= { xcmCONetwareNDS 2 }
    -- stringDisplay

xcmCONetwareSAPInterval         -- SAP Interval (service advertise)
    OBJECT IDENTIFIER ::= { xcmCONetwareSAP 1 }
    -- integerNumber (seconds, 0=none, or 1..n)

--
--          NetBIOS Protocol Suite
--

xcmCONetbiosSuite
    OBJECT IDENTIFIER ::= { xcmCommsConfigTC 25 }
    -- integerTruthValue

xcmCONetbiosDatalinks
    OBJECT IDENTIFIER ::= { xcmCONetbiosSuite 1200 }
    -- integerTruthValue (w/ chain of 'xcmCOOsilan...')

xcmCONetbiosTransports
    OBJECT IDENTIFIER ::= { xcmCONetbiosSuite 1400 }
    -- integerTruthValue

xcmCONetbiosApplications
    OBJECT IDENTIFIER ::= { xcmCONetbiosSuite 1700 }
    -- integerTruthValue
xcmCONetbiosNBP                 -- NBP (NetBIOS Protocol)
    OBJECT IDENTIFIER ::= { xcmCONetbiosSuite 1501 }
    -- integerTruthValue

xcmCONetbiosSNMP                -- SNMP (network mgmt)
    OBJECT IDENTIFIER ::= { xcmCONetbiosSuite 1510 }
    -- integerTruthValue
xcmCONetbiosSNMPv1              -- SNMPv1 (network mgmt)
    OBJECT IDENTIFIER ::= { xcmCONetbiosSuite 1511 }
    -- integerTruthValue
xcmCONetbiosSNMPv2              -- SNMPv2 (network mgmt)
    OBJECT IDENTIFIER ::= { xcmCONetbiosSuite 1512 }
    -- integerTruthValue

xcmCONetbiosSAP                 -- SAP (service advertise)
    OBJECT IDENTIFIER ::= { xcmCONetbiosSuite 1591 }
    -- integerTruthValue

xcmCONetbiosSMB                 -- SMB (Server Message Block)
    OBJECT IDENTIFIER ::= { xcmCONetbiosSuite 1701 }
    -- integerTruthValue
xcmCONetbiosSMBPClient          -- SMB Printing Client
    OBJECT IDENTIFIER ::= { xcmCONetbiosSuite 1702 }
    -- integerTruthValue
xcmCONetbiosSMBPServer          -- SMB Printing Server
    OBJECT IDENTIFIER ::= { xcmCONetbiosSuite 1703 }


    -- integerTruthValue
xcmCONetbiosSMBFClient          -- SMB Filing Client
    OBJECT IDENTIFIER ::= { xcmCONetbiosSuite 1704 }
    -- integerTruthValue
xcmCONetbiosSMBFServer          -- SMB Filing Server
    OBJECT IDENTIFIER ::= { xcmCONetbiosSuite 1705 }
    -- integerTruthValue

xcmCONetbiosNBPName             -- NBP Name
    OBJECT IDENTIFIER ::= { xcmCONetbiosNBP 1 }
    -- stringDisplay
xcmCONetbiosNBPGroupName        -- NBP Group Name
    OBJECT IDENTIFIER ::= { xcmCONetbiosNBP 2 }
    -- stringDisplay
xcmCONetbiosNBPPassword         -- NBP Password
    OBJECT IDENTIFIER ::= { xcmCONetbiosNBP 3 }
    -- stringDisplay (shall ALWAYS be encrypted)
xcmCONetbiosNBPService          -- NBP Service
    OBJECT IDENTIFIER ::= { xcmCONetbiosNBP 4 }
    -- stringDisplay
xcmCONetbiosNBPRemark           -- NBP Remark
    OBJECT IDENTIFIER ::= { xcmCONetbiosNBP 5 }
    -- stringDisplay
xcmCONetbiosNBPOverNetbeui      -- NetBIOS over NetBEUI (native)
    OBJECT IDENTIFIER ::= { xcmCONetbiosNBP 11 }
    -- integerTruthValue
xcmCONetbiosNBPOverInternet     -- NetBIOS over TCP (RFC 1001/1002)
    OBJECT IDENTIFIER ::= { xcmCONetbiosNBP 12 }
    -- integerTruthValue
xcmCONetbiosNBPOverNetware      -- NetBIOS over IPX (Netware)
    OBJECT IDENTIFIER ::= { xcmCONetbiosNBP 13 }
    -- integerTruthValue

xcmCONetbiosSAPInterval         -- SAP Interval (service advertise)
    OBJECT IDENTIFIER ::= { xcmCONetbiosSAP 1 }
    -- integerNumber (seconds, 0=none, or 1..n)

--
--          NetBEUI Protocol Suite
--

xcmCONetbeuiSuite
    OBJECT IDENTIFIER ::= { xcmCommsConfigTC 26 }
    -- integerTruthValue

xcmCONetbeuiDatalinks
    OBJECT IDENTIFIER ::= { xcmCONetbeuiSuite 1200 }
    -- integerTruthValue (w/ chain of 'xcmCOOsilan...')
xcmCONetbeuiLLC                 -- NetBEUI LLC (ISO/IEEE 802.2)
    OBJECT IDENTIFIER ::= { xcmCONetbeuiSuite 1201 }
    -- integerTruthValue
xcmCONetbeuiDLC                 -- NetBEUI DLC (IBM SNA DLC)
    OBJECT IDENTIFIER ::= { xcmCONetbeuiSuite 1202 }
    -- integerTruthValue


--
--          Serial Protocol Suite
--

xcmCOSerialSuite
    OBJECT IDENTIFIER ::= { xcmCommsConfigTC 27 }
    -- integerTruthValue

xcmCOSerialPhysical
    OBJECT IDENTIFIER ::= { xcmCOSerialSuite 1100 }
    -- integerTruthValue
xcmCOSerialSignalType
    OBJECT IDENTIFIER ::= { xcmCOSerialSuite 1101 }
    -- integerEnum (1=none, 2=other, 3=rs232, 4=rs422, 5=v35)
xcmCOSerialDevice
    OBJECT IDENTIFIER ::= { xcmCOSerialSuite 1102 }
    -- integerNumber ('hrDeviceIndex' in IETF HR MIB, or 0=unknown)
xcmCOSerialDeviceName
    OBJECT IDENTIFIER ::= { xcmCOSerialDevice 1 }
    -- stringDisplay ('xcmHrDevInfoName' in HRX MIB, eg, '/dev/com1')
xcmCOSerialSpeed
    OBJECT IDENTIFIER ::= { xcmCOSerialSuite 1103 }
    -- integerNumber (as in 'ifSpeed' in IETF MIB-II)
xcmCOSerialBidirectional
    OBJECT IDENTIFIER ::= { xcmCOSerialSuite 1104 }
    -- integerTruthValue
xcmCOSerialInputTimeout         -- POSIX.1 'VTIME' * 10 (in 'termios.h')
    OBJECT IDENTIFIER ::= { xcmCOSerialSuite 1105 }
    -- integerNumber (seconds, 0=infinite or 1..n)
xcmCOSerialOutputTimeout
    OBJECT IDENTIFIER ::= { xcmCOSerialSuite 1106 }
    -- integerNumber (seconds, 0=infinite or 1..n)
xcmCOSerialConnectorType
    OBJECT IDENTIFIER ::= { xcmCOSerialSuite 1107 }
    -- integerEnum (1=none, 2=other, 3=db9, 4=db25, 5=v35, 6=rj11)
xcmCOSerialMinInputChars        -- POSIX.1 'VMIN' (in 'termios.h')
    OBJECT IDENTIFIER ::= { xcmCOSerialSuite 1108 }
    -- integerNumber (0=infinite or 1..n)
xcmCOSerialMaxInputChars        -- POSIX.1 'nbyte' (in 'read()')
    OBJECT IDENTIFIER ::= { xcmCOSerialSuite 1109 }
    -- integerNumber (0=infinite or 1..n)
xcmCOSerialParity
    OBJECT IDENTIFIER ::= { xcmCOSerialSuite 1111 }
    -- integerEnum (1=none, 2=odd, 3=even, 4=mark, 5=space)
xcmCOSerialDataBits
    OBJECT IDENTIFIER ::= { xcmCOSerialSuite 1112 }
    -- integerNumber (0=default or 5..8)
xcmCOSerialFlowControl
    OBJECT IDENTIFIER ::= { xcmCOSerialSuite 1113 }
    -- integerEnum (1=none, 2=xon/xoff, 3=rts/cts, 4=dtr, 
    -- 5=robustXon/Xoff)
xcmCOSerialStartBits
    OBJECT IDENTIFIER ::= { xcmCOSerialSuite 1114 }


    -- integerEnum (0=default or 1=1 bit, 2=1.5 bits)
xcmCOSerialStopBits
    OBJECT IDENTIFIER ::= { xcmCOSerialSuite 1115 }
    -- integerEnum (0=default or 1=1 bit, 2=2 bits, 3=1.5 bits)
xcmCOSerialDTR                  -- Data Terminal Ready
    OBJECT IDENTIFIER ::= { xcmCOSerialSuite 1121 }
    -- integerEnum (1=fixedHigh, 2=fixedLow, 3=activeHigh, 4=activeLow)

xcmCOSerialDatalinks
    OBJECT IDENTIFIER ::= { xcmCOSerialSuite 1200 }
    -- integerTruthValue

xcmCOSerialProtocol
    OBJECT IDENTIFIER ::= { xcmCOSerialDatalinks 1 }
    -- integerEnum (1=none, 2=other, 3=autoSwitch,
    -- 11=psAutoSwitch, 12=psRaw, 13=psStandard, 14=psBCP, 15=psTBCP,
    -- 16=psAutoSwitchBCP, 17=psAutoSwitchTBCP,
    -- 21=hpAutoSwitch, 22=hpText, 23=hpPCL, 24=hpPJL)

--
--          Parallel Protocol Suite
--

xcmCOParallelSuite
    OBJECT IDENTIFIER ::= { xcmCommsConfigTC 28 }
    -- integerTruthValue

xcmCOParallelPhysical
    OBJECT IDENTIFIER ::= { xcmCOParallelSuite 1100 }
    -- integerTruthValue
xcmCOParallelSignalType
    OBJECT IDENTIFIER ::= { xcmCOParallelSuite 1101 }
    -- integerEnum (1=none, 2=other, 3=centronics, 4=ecp, 5=epp)
xcmCOParallelDevice
    OBJECT IDENTIFIER ::= { xcmCOParallelSuite 1102 }
    -- integerNumber ('hrDeviceIndex' in IETF HR MIB, or 0=unknown)
xcmCOParallelDeviceName
    OBJECT IDENTIFIER ::= { xcmCOParallelDevice 1 }
    -- stringDisplay ('xcmHrDevInfoName' in HRX MIB, eg, '/dev/lpr1')
xcmCOParallelSpeed
    OBJECT IDENTIFIER ::= { xcmCOParallelSuite 1103 }
    -- integerNumber (as in 'ifSpeed' in IETF MIB-II)
xcmCOParallelBidirectional
    OBJECT IDENTIFIER ::= { xcmCOParallelSuite 1104 }
    -- integerTruthValue
xcmCOParallelInputTimeout       -- POSIX.1 'VTIME' * 10 (in 'termios.h')
    OBJECT IDENTIFIER ::= { xcmCOParallelSuite 1105 }
    -- integerNumber (seconds, 0=infinite or 1..n)
xcmCOParallelOutputTimeout
    OBJECT IDENTIFIER ::= { xcmCOParallelSuite 1106 }
    -- integerNumber (seconds, 0=infinite or 1..n)
xcmCOParallelConnectorType
    OBJECT IDENTIFIER ::= { xcmCOParallelSuite 1107 }
    -- integerEnum (1=none, 2=other, 3=centronics, 4=db25)


xcmCOParallelMinInputChars      -- POSIX.1 'VMIN' (in 'termios.h')
    OBJECT IDENTIFIER ::= { xcmCOParallelSuite 1108 }
    -- integerNumber (0=infinite or 1..n)
xcmCOParallelMaxInputChars      -- POSIX.1 'nbyte' (in 'read()')
    OBJECT IDENTIFIER ::= { xcmCOParallelSuite 1109 }
    -- integerNumber (0=infinite or 1..n)
xcmCOParallelParity
    OBJECT IDENTIFIER ::= { xcmCOParallelSuite 1111 }
    -- integerEnum (1=none, 2=odd, 3=even, 4=mark, 5=space)
xcmCOParallelDataBits
    OBJECT IDENTIFIER ::= { xcmCOParallelSuite 1112 }
    -- integerNumber (0=default or 7..8)
xcmCOParallelFlowControl
    OBJECT IDENTIFIER ::= { xcmCOParallelSuite 1113 }
    -- integerEnum (1=none, 2=xon/xoff)

xcmCOParallelDatalinks
    OBJECT IDENTIFIER ::= { xcmCOParallelSuite 1200 }
    -- integerTruthValue

xcmCOParallelProtocol
    OBJECT IDENTIFIER ::= { xcmCOParallelDatalinks 1 }
    -- integerEnum (1=none, 2=other, 3=autoSwitch,
    -- 11=psAutoSwitch, 12=psRaw, 13=psStandard, 14=psBCP, 15=psTBCP,
    -- 16=psAutoSwitchBCP, 17=psAutoSwitchTBCP,
    -- 21=hpAutoSwitch, 22=hpText, 23=hpPCL, 24=hpPJL)

--
--          Direct Print Protocol Suite (Serial/Parallel)
--

xcmCODirectPrintSuite
    OBJECT IDENTIFIER ::= { xcmCommsConfigTC 29 }
    -- integerTruthValue

xcmCODirectPrintPhysical
    OBJECT IDENTIFIER ::= { xcmCODirectPrintSuite 1100 }
    -- integerTruthValue

xcmCODirectPrintDatalinks
    OBJECT IDENTIFIER ::= { xcmCODirectPrintSuite 1200 }
    -- integerTruthValue

xcmCODirectPrintProtocol
    OBJECT IDENTIFIER ::= { xcmCODirectPrintDatalinks 1 }
    -- integerEnum (1=none, 2=other, 3=autoSwitch,
    -- 11=psAutoSwitch, 12=psRaw, 13=psStandard, 14=psBCP, 15=psTBCP,
    -- 16=psAutoSwitchBCP, 17=psAutoSwitchTBCP,
    -- 21=hpAutoSwitch, 22=hpText, 23=hpPCL, 24=hpPJL)

--
--          The Comms Config TC Dummy Group (DO NOT USE)
--
--          DO NOT USE - Present to suppress compiler warnings ONLY!


--
--          Note:  The following objects have 'odd' use of case in their
--          names (ie, 'xCm...'), in order to make obvious their related
--          textual conventions

xCmCommsConfigDummy OBJECT IDENTIFIER ::= { xcmCommsConfigTC 999 }

xCmSnmpNetbiosAddress OBJECT-TYPE
    SYNTAX      XcmSnmpNetbiosAddress
    MAX-ACCESS  not-accessible
    STATUS      current
    DESCRIPTION "Dummy - DO NOT USE"
    ::= { xCmCommsConfigDummy 1 }

xCmCommsConfigGroupSupport OBJECT-TYPE
    SYNTAX      XcmCommsConfigGroupSupport
    MAX-ACCESS  not-accessible
    STATUS      current
    DESCRIPTION "Dummy - DO NOT USE"
    ::= { xCmCommsConfigDummy 2 }

END
