XEROX-PRODUCT-ID-TC DEFINITIONS ::= BEGIN

-- Module:  XCMI Product Identifier Textual Conventions MIB
-- Editors: Paul Gloger and Joe Filion
-- File:    93pidtc.mib
-- Date:    January 17, 1999
-- Version: 3.10.pub

--
--

IMPORTS
    MODULE-IDENTITY, OBJECT-IDENTITY
            FROM SNMPv2-SMI             -- IETF RFC 1442 / 1902
    xeroxCommonMIB
            FROM XEROX-COMMON-MIB;

xcmPidTC MODULE-IDENTITY
    LAST-UPDATED "9901170000Z"
    ORGANIZATION "Xerox Corporation -
        Xerox Common Management Interface (XCMI) Working Group"
    CONTACT-INFO "
                      XCMI Editors
        E-Mail:       xcmieditors@cp10.es.xerox.com

        --
        --
        "
    DESCRIPTION "
        XCMI Product ID Module,
        Version 3.10.pub.

        Copyright (C) 1997-1999 Xerox Corporation. All Rights Reserved."
    ::= { xeroxCommonMIB 62 }
        -- ::= {1.3.6.1.4.1.253.8.62}

xcmPidProductIdentifiers OBJECT-IDENTITY
    STATUS      current
    DESCRIPTION
        "The root of all identifiers defined in this module."
    ::= { xcmPidTC 1 }
        -- ::= {1.3.6.1.4.1.253.8.62.1}

----------------------------------------------------------------
-- Document Centre Systems
----------------------------------------------------------------

xcmPidDocuCentreSystems OBJECT-IDENTITY
    STATUS      current
    DESCRIPTION
        "Document Centre Systems product line identifier
                 (not a complete product identifier)."
    ::= { xcmPidProductIdentifiers 1 }
        -- ::= {1.3.6.1.4.1.253.8.62.1.1}

--
--

-- Document Centre 220  (20 ppm)

xcmPidDC220 OBJECT-IDENTITY
    STATUS      current
    DESCRIPTION
        "Document Centre 220 product type identifier
                 (not a complete product identifier)."
    ::= { xcmPidDocuCentreSystems 8 }
        -- ::= {1.3.6.1.4.1.253.8.62.1.1.8}

xcmPidDC220ST OBJECT-IDENTITY
    STATUS      current
    DESCRIPTION
        "Document Centre 220ST multi-func. system
                 model identifier (not a complete product identifier)."
    ::= { xcmPidDC220 1 }
        -- ::= {1.3.6.1.4.1.253.8.62.1.1.8.1}
            -- => SAP PID string = "181"

xcmPidDC220STV3 OBJECT-IDENTITY
    STATUS      current
    DESCRIPTION
        "Document Centre 220ST multi-func. system
                 second post-launch configuration version, and
                 complete product identifier."
    ::= { xcmPidDC220ST 3 }
        -- ::= {1.3.6.1.4.1.253.8.62.1.1.8.1.3}

-- Document Centre 230  (30 ppm)

xcmPidDC230 OBJECT-IDENTITY
    STATUS      current
    DESCRIPTION
        "Document Centre 230 product type identifier
                 (not a complete product identifier)."
    ::= { xcmPidDocuCentreSystems 3 }
        -- ::= {1.3.6.1.4.1.253.8.62.1.1.3}

xcmPidDC230ST OBJECT-IDENTITY
    STATUS      current
    DESCRIPTION
        "Document Centre 230ST multi-func. system
                 model identifier (not a complete product identifier)."
    ::= { xcmPidDC230 1 }
        -- ::= {1.3.6.1.4.1.253.8.62.1.1.3.1}
            -- => SAP PID string = "131"

xcmPidDC230STV1 OBJECT-IDENTITY
    STATUS      current
    DESCRIPTION
        "Document Centre 230ST multi-func. system
                 launch configuration version, and
                 complete product identifier."
    ::= { xcmPidDC230ST 1 }
        -- ::= {1.3.6.1.4.1.253.8.62.1.1.3.1.1}

xcmPidDC230STV2 OBJECT-IDENTITY
    STATUS      current
    DESCRIPTION
        "Document Centre 230ST multi-func. system
                 first post-launch configuration version, and
                 complete product identifier."
    ::= { xcmPidDC230ST 2 }
        -- ::= {1.3.6.1.4.1.253.8.62.1.1.3.1.2}

xcmPidDC230STV3 OBJECT-IDENTITY
    STATUS      current
    DESCRIPTION
        "Document Centre 230ST multi-func. system
                 second post-launch configuration version, and
                 complete product identifier."
    ::= { xcmPidDC230ST 3 }
        -- ::= {1.3.6.1.4.1.253.8.62.1.1.3.1.3}

xcmPidDC230LP OBJECT-IDENTITY
    STATUS      current
    DESCRIPTION
        "Document Centre 230LP laser printer
                 model identifier (not a complete product identifier)."
    ::= { xcmPidDC230 2 }
        -- ::= {1.3.6.1.4.1.253.8.62.1.1.3.2}
            -- => SAP PID string = "132"

xcmPidDC230LPV1 OBJECT-IDENTITY
    STATUS      current
    DESCRIPTION
        "Document Centre 230LP laser printer
                 launch configuration version, and
                 complete product identifier."
    ::= { xcmPidDC230LP 1 }
        -- ::= {1.3.6.1.4.1.253.8.62.1.1.3.2.1}

xcmPidDC230LPV2 OBJECT-IDENTITY
    STATUS      current
    DESCRIPTION
        "Document Centre 230LP laser printer
                 first post-launch configuration version, and
                 complete product identifier."
    ::= { xcmPidDC230LP 2 }
        -- ::= {1.3.6.1.4.1.253.8.62.1.1.3.2.2}

xcmPidDC230LPV3 OBJECT-IDENTITY
    STATUS      current
    DESCRIPTION
        "Document Centre 230LP laser printer
                 second post-launch configuration version, and
                 complete product identifier."
    ::= { xcmPidDC230LP 3 }
        -- ::= {1.3.6.1.4.1.253.8.62.1.1.3.2.3}

-- Document Centre 240  (40 ppm)

xcmPidDC240 OBJECT-IDENTITY
    STATUS      current
    DESCRIPTION
        "Document Centre 240 product type identifier
                 (not a complete product identifier)."
    ::= { xcmPidDocuCentreSystems 5 }
        -- ::= {1.3.6.1.4.1.253.8.62.1.1.5}

xcmPidDC240ST OBJECT-IDENTITY
    STATUS      current
    DESCRIPTION
        "Document Centre 240ST multi-func. system
                 model identifier (not a complete product identifier)."
    ::= { xcmPidDC240 1 }
        -- ::= {1.3.6.1.4.1.253.8.62.1.1.5.1}
            -- => SAP PID string = "151"

xcmPidDC240STV1 OBJECT-IDENTITY
    STATUS      current
    DESCRIPTION
        "Document Centre 240ST multi-func. system launch configuration
                 version, and complete product identifier."
    ::= { xcmPidDC240ST 1 }
        -- ::= {1.3.6.1.4.1.253.8.62.1.1.5.1.1}

xcmPidDC240STV2 OBJECT-IDENTITY
    STATUS      current
    DESCRIPTION
        "Document Centre 240ST multi-func. system
                 first post-launch configuration version, and
                 complete product identifier."
    ::= { xcmPidDC240ST 2 }
        -- ::= {1.3.6.1.4.1.253.8.62.1.1.5.1.2}

-- Document Centre 255  (55 ppm)

xcmPidDC255 OBJECT-IDENTITY
    STATUS      current
    DESCRIPTION
        "Document Centre 255 product type identifier
                 (not a complete product identifier)."
    ::= { xcmPidDocuCentreSystems 7 }
        -- ::= {1.3.6.1.4.1.253.8.62.1.1.7}

xcmPidDC255ST OBJECT-IDENTITY
    STATUS      current
    DESCRIPTION
        "Document Centre 255ST multi-func. system
                 model identifier (not a complete product identifier)."
    ::= { xcmPidDC255 1 }
        -- ::= {1.3.6.1.4.1.253.8.62.1.1.7.1}
            -- => SAP PID string = "171"

xcmPidDC255STV1 OBJECT-IDENTITY
    STATUS      current
    DESCRIPTION
        "Document Centre 255ST multi-func. system launch configuration
                 version, and complete product identifier."
    ::= { xcmPidDC255ST 1 }
        -- ::= {1.3.6.1.4.1.253.8.62.1.1.7.1.1}

xcmPidDC255STV2 OBJECT-IDENTITY
    STATUS      current
    DESCRIPTION
        "Document Centre 255ST multi-func. system
                 first post-launch configuration version, and
                 complete product identifier."
    ::= { xcmPidDC255ST 2 }
        -- ::= {1.3.6.1.4.1.253.8.62.1.1.7.1.2}

xcmPidDC255LP OBJECT-IDENTITY
    STATUS      current
    DESCRIPTION
        "Document Centre 255LP laser printer
                 model identifier (not a complete product identifier)."
    ::= { xcmPidDC255 2 }
        -- ::= {1.3.6.1.4.1.253.8.62.1.1.7.2}
            -- => SAP PID string = "172"

xcmPidDC255LPV1 OBJECT-IDENTITY
    STATUS      current
    DESCRIPTION
        "Document Centre 255LP laser printer launch configuration
                 version, and complete product identifier."
    ::= { xcmPidDC255LP 1 }
        -- ::= {1.3.6.1.4.1.253.8.62.1.1.7.2.1}

xcmPidDC255LPV2 OBJECT-IDENTITY
    STATUS      current
    DESCRIPTION
        "Document Centre 255LP laser printer
                 first post-launch configuration version, and
                 complete product identifier."
    ::= { xcmPidDC255LP 2 }
        -- ::= {1.3.6.1.4.1.253.8.62.1.1.7.2.2}

-- Document Centre 265  (65 ppm)

xcmPidDC265 OBJECT-IDENTITY
    STATUS      current
    DESCRIPTION
        "Document Centre 265 product type identifier
                 (not a complete product identifier)."
    ::= { xcmPidDocuCentreSystems 4 }
        -- ::= {1.3.6.1.4.1.253.8.62.1.1.4}

xcmPidDC265ST OBJECT-IDENTITY
    STATUS      current
    DESCRIPTION
        "Document Centre 265ST multi-func. system
                 model identifier (not a complete product identifier)."
    ::= { xcmPidDC265 1 }
        -- ::= {1.3.6.1.4.1.253.8.62.1.1.4.1}
            -- => SAP PID string = "141"

xcmPidDC265STV1 OBJECT-IDENTITY
    STATUS      current
    DESCRIPTION
        "Document Centre 265ST multi-func. system launch configuration
                 version, and complete product identifier."
    ::= { xcmPidDC265ST 1 }
        -- ::= {1.3.6.1.4.1.253.8.62.1.1.4.1.1}

xcmPidDC265STV2 OBJECT-IDENTITY
    STATUS      current
    DESCRIPTION
        "Document Centre 265ST multi-func. system
                 first post-launch configuration version, and
                 complete product identifier."
    ::= { xcmPidDC265ST 2 }
        -- ::= {1.3.6.1.4.1.253.8.62.1.1.4.1.2}

xcmPidDC265LP OBJECT-IDENTITY
    STATUS      current
    DESCRIPTION
        "Document Centre 265LP laser printer
                 model identifier (not a complete product identifier)."
    ::= { xcmPidDC265 2 }
        -- ::= {1.3.6.1.4.1.253.8.62.1.1.4.2}
            -- => SAP PID string = "142"

xcmPidDC265LPV1 OBJECT-IDENTITY
    STATUS      current
    DESCRIPTION
        "Document Centre 265LP laser printer launch configuration
                 version, and complete product identifier."
    ::= { xcmPidDC265LP 1 }
        -- ::= {1.3.6.1.4.1.253.8.62.1.1.4.2.1}

xcmPidDC265LPV2 OBJECT-IDENTITY
    STATUS      current
    DESCRIPTION
        "Document Centre 265LP laser printer
                 first post-launch configuration version, and
                 complete product identifier."
    ::= { xcmPidDC265LP 2 }
        -- ::= {1.3.6.1.4.1.253.8.62.1.1.4.2.2}

--
--

----------------------------------------------------------------
-- Desktop DocuPrint Printers
----------------------------------------------------------------

xcmPidDesktopDocuPrintPrinters OBJECT-IDENTITY
    STATUS      current
    DESCRIPTION
        "Desktop DocuPrint Printers product line identifier
                 (not a complete product identifier)."
    ::= { xcmPidProductIdentifiers 2 }
        -- ::= {1.3.6.1.4.1.253.8.62.1.2}

--
--

-- Desktop DocuPrint 4517

xcmPid4517 OBJECT-IDENTITY
    STATUS      current
    DESCRIPTION
        "Desktop DocuPrint 4517 product type identifier
                 (not a complete product identifier)."
    ::= { xcmPidDesktopDocuPrintPrinters 2 }
        -- ::= {1.3.6.1.4.1.253.8.62.1.2.2}

xcmPid4517PlusM1 OBJECT-IDENTITY
    STATUS      current
    DESCRIPTION
        "Desktop DocuPrint 4517+ launch configuration model identifier
                 (not a complete product identifier)."
    ::= { xcmPid4517 1 }
        -- ::= {1.3.6.1.4.1.253.8.62.1.2.2.1}
            -- => SAP PID string = "221"

xcmPid4517PlusM1V1 OBJECT-IDENTITY
    STATUS      current
    DESCRIPTION
        "Desktop DocuPrint 4517+ launch configuration model and version,
                 and complete product identifier."
    ::= { xcmPid4517PlusM1 1 }
        -- ::= {1.3.6.1.4.1.253.8.62.1.2.2.1.1}

-- Desktop DocuPrint N17

xcmPidDocuPrintN17 OBJECT-IDENTITY
    STATUS      current
    DESCRIPTION
        "Desktop DocuPrint N17 launch configuration model
                 identifier (not a complete product identifier)."
    ::= { xcmPid4517 2 }
        -- ::= {1.3.6.1.4.1.253.8.62.1.2.2.2}
            -- => SAP PID string = "222"

xcmPidDocuPrintN17V1 OBJECT-IDENTITY
    STATUS      current
    DESCRIPTION
        "Desktop DocuPrint N17 launch configuration model and
                 version, and complete product identifier."
    ::= { xcmPidDocuPrintN17 1 }
        -- ::= {1.3.6.1.4.1.253.8.62.1.2.2.2.1}

-- Desktop DocuPrint C55

xcmPidDocuPrintC55 OBJECT-IDENTITY
    STATUS      current
    DESCRIPTION
        "Desktop DocuPrint C55 product type identifier
                 (not a complete product identifier)."
    ::= { xcmPidDesktopDocuPrintPrinters 3 }
        -- ::= {1.3.6.1.4.1.253.8.62.1.2.3}

xcmPidDocuPrintC55M1 OBJECT-IDENTITY
    STATUS      current
    DESCRIPTION
        "Desktop DocuPrint C55 launch configuration model identifier
                 (not a complete product identifier)."
    ::= { xcmPidDocuPrintC55 1 }
        -- ::= {1.3.6.1.4.1.253.8.62.1.2.3.1}
            -- => SAP PID string = "231"

xcmPidDocuPrintC55M1V1 OBJECT-IDENTITY
    STATUS      current
    DESCRIPTION
        "Desktop DocuPrint C55 launch configuration model and version,
                 and complete product identifier."
    ::= { xcmPidDocuPrintC55M1 1 }
        -- ::= {1.3.6.1.4.1.253.8.62.1.2.3.1.1}

xcmPidDocuPrintC55M1V2 OBJECT-IDENTITY
    STATUS      current
    DESCRIPTION
        "Desktop DocuPrint C55 launch configuration model /
                 post-launch configuration version,
                 and complete product identifier."
    ::= { xcmPidDocuPrintC55M1 2 }
        -- ::= {1.3.6.1.4.1.253.8.62.1.2.3.1.2}

-- Desktop DocuPrint NC60

xcmPidDocuPrintNC60 OBJECT-IDENTITY
    STATUS      current
    DESCRIPTION
        "Desktop DocuPrint NC60 launch configuration model identifier
                 (not a complete product identifier)."
    ::= { xcmPidDocuPrintC55 2 }
        -- ::= {1.3.6.1.4.1.253.8.62.1.2.3.2}
            -- => SAP PID string = "232"

xcmPidDocuPrintNC60V1 OBJECT-IDENTITY
    STATUS      current
    DESCRIPTION
        "Desktop DocuPrint NC60 launch configuration model and version,
                 and complete product identifier."
    ::= { xcmPidDocuPrintNC60 1 }
        -- ::= {1.3.6.1.4.1.253.8.62.1.2.3.2.1}

----------------------------------------------------------------
-- WorkGroup & MidRange DocuPrint Printers
----------------------------------------------------------------

xcmPidWorkGroupDocuPrintPrinters OBJECT-IDENTITY
    STATUS      current
    DESCRIPTION
        "WorkGroup & MidRange DocuPrint Printers product line identifier
                 (not a complete product identifier)."
    ::= { xcmPidProductIdentifiers 3 }
        -- ::= {1.3.6.1.4.1.253.8.62.1.3}

--
--

-- WorkGroup DocuPrint Nnn

xcmPidDocuPrintNnn OBJECT-IDENTITY
    STATUS      current
    DESCRIPTION
        "WorkGroup DocuPrint Nnn product type identifier
                 (not a complete product identifier)."
    ::= { xcmPidWorkGroupDocuPrintPrinters 2 }
        -- ::= {1.3.6.1.4.1.253.8.62.1.3.2}

xcmPidDocuPrintN32 OBJECT-IDENTITY
    STATUS      current
    DESCRIPTION
        "WorkGroup DocuPrint N32 model identifier
                 (not a complete product identifier)."
    ::= { xcmPidDocuPrintNnn 1 }
        -- ::= {1.3.6.1.4.1.253.8.62.1.3.2.1}
            -- => SAP PID string = "321"

xcmPidDocuPrintN32V1 OBJECT-IDENTITY
    STATUS      current
    DESCRIPTION
        "WorkGroup DocuPrint N32 launch configuration version,
                 and complete product identifier."
    ::= { xcmPidDocuPrintN32 1 }
        -- ::= {1.3.6.1.4.1.253.8.62.1.3.2.1.1}

xcmPidDocuPrintN32V2 OBJECT-IDENTITY
    STATUS      current
    DESCRIPTION
        "WorkGroup DocuPrint N32 post-launch configuration version,
                 and complete product identifier."
    ::= { xcmPidDocuPrintN32 2 }
        -- ::= {1.3.6.1.4.1.253.8.62.1.3.2.1.2}

xcmPidDocuPrintN24 OBJECT-IDENTITY
    STATUS      current
    DESCRIPTION
        "WorkGroup DocuPrint N24 model identifier
                 (not a complete product identifier)."
    ::= { xcmPidDocuPrintNnn 2 }
        -- ::= {1.3.6.1.4.1.253.8.62.1.3.2.2}
            -- => SAP PID string = "322"

xcmPidDocuPrintN24V1 OBJECT-IDENTITY
    STATUS      current
    DESCRIPTION
        "WorkGroup DocuPrint N24 launch configuration version,
                 and complete product identifier."
    ::= { xcmPidDocuPrintN24 1 }
        -- ::= {1.3.6.1.4.1.253.8.62.1.3.2.2.1}

xcmPidDocuPrintN24V2 OBJECT-IDENTITY
    STATUS      current
    DESCRIPTION
        "WorkGroup DocuPrint N24 post-launch configuration version,
                 and complete product identifier."
    ::= { xcmPidDocuPrintN24 2 }
        -- ::= {1.3.6.1.4.1.253.8.62.1.3.2.2.2}

xcmPidDocuPrintN40 OBJECT-IDENTITY
    STATUS      current
    DESCRIPTION
        "WorkGroup DocuPrint N40 model identifier
                 (not a complete product identifier)."
    ::= { xcmPidDocuPrintNnn 3 }
        -- ::= {1.3.6.1.4.1.253.8.62.1.3.2.3}
            -- => SAP PID string = "323"

xcmPidDocuPrintN40V1 OBJECT-IDENTITY
    STATUS      current
    DESCRIPTION
        "WorkGroup DocuPrint N40 launch configuration version,
                 and complete product identifier."
    ::= { xcmPidDocuPrintN40 1 }
        -- ::= {1.3.6.1.4.1.253.8.62.1.3.2.3.1}

--
--

----------------------------------------------------------------
-- DocuPrint NPS (Network Printing Systems) Printers
----------------------------------------------------------------

xcmPidDocuPrintNPS OBJECT-IDENTITY
    STATUS      current
    DESCRIPTION
        "DocuPrint NPS (Network Printing Systems) product line
                 identifier (not a complete product identifier)."
    ::= { xcmPidProductIdentifiers 9 }
        -- ::= {1.3.6.1.4.1.253.8.62.1.9}

-- DocuPrint NPS DP4050 Printer

xcmPidDP4050NPS OBJECT-IDENTITY
    STATUS      current
    DESCRIPTION
        "DocuPrint NPS DP4050 product type identifier
                 (not a complete product identifier)."
    ::= { xcmPidDocuPrintNPS 1 }
        -- ::= {1.3.6.1.4.1.253.8.62.1.9.1}

xcmPidDP4050NPSM1 OBJECT-IDENTITY
    STATUS      current
    DESCRIPTION
        "DocuPrint NPS DP4050 launch configuration model identifier
                 (not a complete product identifier)."
    ::= { xcmPidDP4050NPS 1 }
        -- ::= {1.3.6.1.4.1.253.8.62.1.9.1.1}
            -- => SAP PID string = "911"

xcmPidDP4050NPSM1V1 OBJECT-IDENTITY
    STATUS      current
    DESCRIPTION
        "DocuPrint NPS DP4050 launch configuration version,
                 and complete product identifier."
    ::= { xcmPidDP4050NPSM1 1 }
        -- ::= {1.3.6.1.4.1.253.8.62.1.9.1.1.1}

-- DocuPrint NPS DP4090 Printer

xcmPidDP4090NPS OBJECT-IDENTITY
    STATUS      current
    DESCRIPTION
        "DocuPrint NPS DP4090 product type identifier
                 (not a complete product identifier)."
    ::= { xcmPidDocuPrintNPS 2 }
        -- ::= {1.3.6.1.4.1.253.8.62.1.9.2}

xcmPidDP4090NPSM1 OBJECT-IDENTITY
    STATUS      current
    DESCRIPTION
        "DocuPrint NPS DP4090 launch configuration model identifier
                 (not a complete product identifier)."
    ::= { xcmPidDP4090NPS 1 }
        -- ::= {1.3.6.1.4.1.253.8.62.1.9.2.1}
            -- => SAP PID string = "921"

xcmPidDP4090NPSM1V1 OBJECT-IDENTITY
    STATUS      current
    DESCRIPTION
        "DocuPrint NPS DP4090 launch configuration version,
                 and complete product identifier."
    ::= { xcmPidDP4090NPSM1 1 }
        -- ::= {1.3.6.1.4.1.253.8.62.1.9.2.1.1}

-- DocuPrint NPS DP4850 Printer

xcmPidDP4850NPS OBJECT-IDENTITY
    STATUS      current
    DESCRIPTION
        "DocuPrint NPS DP4850 product type identifier
                 (not a complete product identifier)."
    ::= { xcmPidDocuPrintNPS 3 }
        -- ::= {1.3.6.1.4.1.253.8.62.1.9.3}

xcmPidDP4850NPSM1 OBJECT-IDENTITY
    STATUS      current
    DESCRIPTION
        "DocuPrint NPS DP4850 launch configuration model identifier
                 (not a complete product identifier)."
    ::= { xcmPidDP4850NPS 1 }
        -- ::= {1.3.6.1.4.1.253.8.62.1.9.3.1}
            -- => SAP PID string = "931"

xcmPidDP4850NPSM1V1 OBJECT-IDENTITY
    STATUS      current
    DESCRIPTION
        "DocuPrint NPS DP4850 launch configuration version,
                 and complete product identifier."
    ::= { xcmPidDP4850NPSM1 1 }
        -- ::= {1.3.6.1.4.1.253.8.62.1.9.3.1.1}

-- DocuPrint NPS DP4890 Printer

xcmPidDP4890NPS OBJECT-IDENTITY
    STATUS      current
    DESCRIPTION
        "DocuPrint NPS DP4890 product type identifier
                 (not a complete product identifier)."
    ::= { xcmPidDocuPrintNPS 4 }
        -- ::= {1.3.6.1.4.1.253.8.62.1.9.4}

xcmPidDP4890NPSM1 OBJECT-IDENTITY
    STATUS      current
    DESCRIPTION
        "DocuPrint NPS DP4890 launch configuration model identifier
                 (not a complete product identifier)."
    ::= { xcmPidDP4890NPS 1 }
        -- ::= {1.3.6.1.4.1.253.8.62.1.9.4.1}
            -- => SAP PID string = "941"

xcmPidDP4890NPSM1V1 OBJECT-IDENTITY
    STATUS      current
    DESCRIPTION
        "DocuPrint NPS DP4890 launch configuration version,
                 and complete product identifier."
    ::= { xcmPidDP4890NPSM1 1 }
        -- ::= {1.3.6.1.4.1.253.8.62.1.9.4.1.1}

-- DocuPrint NPS DP4635 Printer

xcmPidDP4635NPS OBJECT-IDENTITY
    STATUS      current
    DESCRIPTION
        "DocuPrint NPS DP4635 product type identifier
                 (not a complete product identifier)."
    ::= { xcmPidDocuPrintNPS 5 }
        -- ::= {1.3.6.1.4.1.253.8.62.1.9.5}

xcmPidDP4635NPSM1 OBJECT-IDENTITY
    STATUS      current
    DESCRIPTION
        "DocuPrint NPS DP4635 launch configuration model identifier
                 (not a complete product identifier)."
    ::= { xcmPidDP4635NPS 1 }
        -- ::= {1.3.6.1.4.1.253.8.62.1.9.5.1}
            -- => SAP PID string = "951"

xcmPidDP4635NPSM1V1 OBJECT-IDENTITY
    STATUS      current
    DESCRIPTION
        "DocuPrint NPS DP4635 launch configuration version,
                 and complete product identifier."
    ::= { xcmPidDP4635NPSM1 1 }
        -- ::= {1.3.6.1.4.1.253.8.62.1.9.5.1.1}

-- DocuPrint NPS DP4635 Micr Printer

xcmPidDP4635NPSMicr OBJECT-IDENTITY
    STATUS      current
    DESCRIPTION
        "DocuPrint NPS DP4635 Micr launch configuration model identifier
                 (not a complete product identifier)."
    ::= { xcmPidDP4635NPS 2 }
        -- ::= {1.3.6.1.4.1.253.8.62.1.9.5.2}
            -- => SAP PID string = "952"

xcmPidDP4635NPSMicrV1 OBJECT-IDENTITY
    STATUS      current
    DESCRIPTION
        "DocuPrint NPS DP4635 Micr launch configuration version,
                 and complete product identifier."
    ::= { xcmPidDP4635NPSMicr 1 }
        -- ::= {1.3.6.1.4.1.253.8.62.1.9.5.2.1}

-- DocuPrint NPS DP180 Printer

xcmPidDP180NPS OBJECT-IDENTITY
    STATUS      current
    DESCRIPTION
        "DocuPrint NPS DP180 product type identifier
                 (not a complete product identifier)."
    ::= { xcmPidDocuPrintNPS 6 }
        -- ::= {1.3.6.1.4.1.253.8.62.1.9.6}

xcmPidDP180NPSM1 OBJECT-IDENTITY
    STATUS      current
    DESCRIPTION
        "DocuPrint NPS DP180 launch configuration model identifier
                 (not a complete product identifier)."
    ::= { xcmPidDP180NPS 1 }
        -- ::= {1.3.6.1.4.1.253.8.62.1.9.6.1}
            -- => SAP PID string = "961"

xcmPidDP180NPSM1V1 OBJECT-IDENTITY
    STATUS      current
    DESCRIPTION
        "DocuPrint NPS DP180 launch configuration version,
                 and complete product identifier."
    ::= { xcmPidDP180NPSM1 1 }
        -- ::= {1.3.6.1.4.1.253.8.62.1.9.6.1.1}

-- DocuPrint NPS DP180 Micr Printer

xcmPidDP180NPSMicr OBJECT-IDENTITY
    STATUS      current
    DESCRIPTION
        "DocuPrint NPS DP180 Micr launch configuration model identifier
                 (not a complete product identifier)."
    ::= { xcmPidDP180NPS 2 }
        -- ::= {1.3.6.1.4.1.253.8.62.1.9.6.2}
            -- => SAP PID string = "962"

xcmPidDP180NPSMicrV1 OBJECT-IDENTITY
    STATUS      current
    DESCRIPTION
        "DocuPrint NPS DP180 Micr launch configuration version,
                 and complete product identifier."
    ::= { xcmPidDP180NPSMicr 1 }
        -- ::= {1.3.6.1.4.1.253.8.62.1.9.6.2.1}

-- DocuPrint NPS DP96 Printer

xcmPidDP96NPS OBJECT-IDENTITY
    STATUS      current
    DESCRIPTION
        "DocuPrint NPS DP96 product type identifier
                 (not a complete product identifier)."
    ::= { xcmPidDocuPrintNPS 7 }
        -- ::= {1.3.6.1.4.1.253.8.62.1.9.7}

xcmPidDP96NPSM1 OBJECT-IDENTITY
    STATUS      current
    DESCRIPTION
        "DocuPrint NPS DP96 launch configuration model identifier
                 (not a complete product identifier)."
    ::= { xcmPidDP96NPS 1 }
        -- ::= {1.3.6.1.4.1.253.8.62.1.9.7.1}
            -- => SAP PID string = "971"

xcmPidDP96NPSM1V1 OBJECT-IDENTITY
    STATUS      current
    DESCRIPTION
        "DocuPrint NPS DP96 launch configuration version,
                 and complete product identifier."
    ::= { xcmPidDP96NPSM1 1 }
        -- ::= {1.3.6.1.4.1.253.8.62.1.9.7.1.1}

-- DocuPrint NPS DP96 Micr Printer

xcmPidDP96NPSMicr OBJECT-IDENTITY
    STATUS      current
    DESCRIPTION
        "DocuPrint NPS DP96 Micr launch configuration model identifier
                 (not a complete product identifier)."
    ::= { xcmPidDP96NPS 2 }
        -- ::= {1.3.6.1.4.1.253.8.62.1.9.7.2}
            -- => SAP PID string = "972"

xcmPidDP96NPSMicrV1 OBJECT-IDENTITY
    STATUS      current
    DESCRIPTION
        "DocuPrint NPS DP96 Micr launch configuration version,
                 and complete product identifier."
    ::= { xcmPidDP96NPSMicr 1 }
        -- ::= {1.3.6.1.4.1.253.8.62.1.9.7.2.1}

--
--

END
