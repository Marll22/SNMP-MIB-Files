XYPLEX-DECNET-MIB DEFINITIONS ::= BEGIN
            
                    IMPORTS
                            enterprises
                                    FROM RFC1155-SMI
                            OBJECT-TYPE
                                    FROM RFC-1212;
            
            xyplex          OBJECT IDENTIFIER ::= { enterprises 33 }
            decnet          OBJECT IDENTIFIER ::= { xyplex 14 }
            
            -- Xyplex Internet subgroups
            
            rcp             OBJECT IDENTIFIER ::= { decnet 1 }
            
            --  This MIB module uses the extended OBJECT-TYPE macro as
            --  defined in [9]
            
            --  this is the MIB module for Xyplex DECnet
            --  implementations
























            
            

            
            
            
            
            -- the Remote Console group
            
            -- Implementation of this group is mandatory for all Xyplex
            -- systems that implement DECnet remote console (RCP)
            
            rcpRemoteAddress OBJECT-TYPE
                SYNTAX OCTET STRING (SIZE (0..6))
                ACCESS read-only
                STATUS mandatory
                DESCRIPTION
                    "If a remote console session exists, the Ethernet 
                    address of the remote partner, otherwise zero 
                    length."
                ::= { rcp 1 }
            
END
