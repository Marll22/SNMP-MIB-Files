XYPLEX-INTERNET-MIB DEFINITIONS ::= BEGIN
            
                    IMPORTS
                            enterprises, Counter, Gauge, IpAddress
                                    FROM RFC1155-SMI
                            DisplayString
                                    FROM SNMPv2-TC
                            OBJECT-TYPE
                                    FROM RFC-1212
                            DateTime, AddressType
                                    FROM XYPLEX-SYSTEM-MIB;
            
            xyplex          OBJECT IDENTIFIER ::= { enterprises 33 }
            xInternetDep    OBJECT IDENTIFIER ::= { xyplex 4 }
            xInternet       OBJECT IDENTIFIER ::= { xyplex 10 }
            
            -- Xyplex Internet subgroups
            
            xIp             OBJECT IDENTIFIER ::= { xInternet 1 }
            xTcp            OBJECT IDENTIFIER ::= { xInternet 2 }
            snmpAgent       OBJECT IDENTIFIER ::= { xInternet 3 }
            domainResolver  OBJECT IDENTIFIER ::= { xInternet 4 }
            slip            OBJECT IDENTIFIER ::= { xInternet 5 }
            telnet          OBJECT IDENTIFIER ::= { xInternet 6 }
            tn3270          OBJECT IDENTIFIER ::= { xInternet 7 }
            kerberos        OBJECT IDENTIFIER ::= { xInternet 8 }
            portSecurity    OBJECT IDENTIFIER ::= { xInternet 9 }
            xremote         OBJECT IDENTIFIER ::= { xInternet 10 }
            rotary          OBJECT IDENTIFIER ::= { xInternet 11 }
            xEgp            OBJECT IDENTIFIER ::= { xInternet 12 }
            xospf           OBJECT IDENTIFIER ::= { xInternet 13 }
            routerIp        OBJECT IDENTIFIER ::= { xInternet 14 }
            routerUdp       OBJECT IDENTIFIER ::= { xInternet 15 }
            routerPolicy    OBJECT IDENTIFIER ::= { xInternet 16 }
            
            -- This is a MIB module for all Xyplex systems that
            -- implement IP







            
            
            
            
            
            
            -- the IP group
            
            -- Implementation of this group is mandatory for all Xyplex
            -- systems that implement IP
            
            ipGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xIp 1 }
            
            ipGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xIp 2 }
            
            ipAutoSubnetMask OBJECT-TYPE
                SYNTAX INTEGER { disabled(1), enabled(2) }
                ACCESS read-write
                STATUS mandatory
                DESCRIPTION
                    "A control for automatic determination of subnet 
                    mask.  'disabled' indicates the system must use the 
                    mask as configured by the network manager.  
                    'enabled' indicates that the system is to 
                    automatically change the subnet mask when the 
                    system's Internet address is changed.  Corresponds 
                    directly to SERVER INTERNET SUBNET MASK 
                    AUTOCONFIGURE and the value labeled 'Subnet Mask 
                    Autoconfigure:' in the SERVER INTERNET 
                    CHARACTERISTICS display."

            
            
            
            
            
            
                ::= { xIp 3 }
            
            ipReassembly OBJECT-TYPE
                SYNTAX INTEGER { disabled(1), enabled(2) }
                ACCESS read-write
                STATUS mandatory
                DESCRIPTION
                    "A control for reassembly of IP fragments.  
                    Corresponds directly to SERVER INTERNET REASSEMBLY 
                    and the value labeled 'Reassembly:' in the SERVER 
                    INTERNET CHARACTERISTICS display."
                ::= { xIp 4 }


































            
            
            
            
            
            
            -- the TCP group
            
            -- Implementation of this group is mandatory for all Xyplex
            -- systems that implement TCP
            
            -- the TCP Character Port table
            
            tcpPortTable OBJECT-TYPE
                SYNTAX SEQUENCE OF TcpPortEntry
                ACCESS not-accessible
                STATUS mandatory
                DESCRIPTION
                    "A list of TCP character port entries."
                ::= { xTcp 1 }
            
            tcpPortEntry OBJECT-TYPE
                SYNTAX TcpPortEntry
                ACCESS not-accessible
                STATUS mandatory
                DESCRIPTION
                    "TCP parameter values for a character port."
                INDEX { tcpPortIndex }
                ::= { tcpPortTable 1 }
            
            TcpPortEntry ::=
                SEQUENCE {
                    tcpPortIndex
                        INTEGER,
                    tcpPortConnectByAddress
                        INTEGER,
                    tcpPortWindowSize
                        INTEGER
                }
            
            tcpPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tcpPortEntry 1 }
            

            
            
            
            
            
            
            tcpPortConnectByAddress OBJECT-TYPE
                SYNTAX INTEGER { disabled(1), enabled(2) }
                ACCESS read-write
                STATUS mandatory
                DESCRIPTION
                    "A control for requesting outgoing connection by 
                    internet address.  'disabled' indicates outgoing 
                    connections must be by Domain name.  'enabled' 
                    indicates that outgoing connections may be requested 
                    by internet address.  Corresponds directly to PORT 
                    INTERNET CONNECTIONS and the presence of the label 
                    'Internet Connections' following the label 'Enabled 
                    Characteristics:' in the PORT CHARACTERISTICS 
                    display."
                ::= { tcpPortEntry 2 }
            
            tcpPortWindowSize OBJECT-TYPE
                SYNTAX INTEGER (64..8192)
                ACCESS read-write
                STATUS mandatory
                DESCRIPTION
                    "Size of the TCP window for TCP connections on the 
                    port.  Corresponds directly to PORT INTERNET TCP 
                    WINDOW SIZE and the value labeled 'TCP Window Size:' 
                    in the PORT ALTERNATE CHARACTERISTICS display."
                ::= { tcpPortEntry 3 }




















            
            
            
            
            
            
            -- the SNMP Agent group
            
            -- Implementation of this group is mandatory for all Xyplex
            -- systems that implement SNMP
            
            snmpAgentGetCommunity OBJECT-TYPE
                SYNTAX DisplayString (SIZE (0..32))
                ACCESS read-write
                STATUS mandatory
                DESCRIPTION
                    "The SNMP community name allowed to perform 
                    get-requests or get-next requests to this agent.  
                    Use of this value is case-insensitive.  If the size 
                    is 0, the agent does not check the community name 
                    for these operations.  Corresponds directly to 
                    SERVER INTERNET SNMP GET COMMUNITY and the value 
                    labeled 'Get Community:' in the SERVER INTERNET SNMP 
                    CHARACTERISTICS display."
                ::= { snmpAgent 1 }
            
            snmpAgentSetCommunity OBJECT-TYPE
                SYNTAX DisplayString (SIZE (0..32))
                ACCESS read-write
                STATUS mandatory
                DESCRIPTION
                    "The SNMP community name allowed to perform 
                    set-requests to this agent.  Use of this value is 
                    case-insensitive.  If the size is 0, the agent does 
                    not check the community name for these operations.  
                    Corresponds directly to SERVER INTERNET SNMP SET 
                    COMMUNITY and the value labeled 'Set Community:' in 
                    the SERVER INTERNET SNMP CHARACTERISTICS display."
                ::= { snmpAgent 2 }
            
            snmpAgentTrapCommunity OBJECT-TYPE
                SYNTAX DisplayString (SIZE (0..32))
                ACCESS read-write
                STATUS mandatory
                DESCRIPTION
                    "The SNMP community name sent in traps from this 
                    agent.  Use of this value preserves case.  
                    Corresponds directly to SERVER INTERNET SNMP TRAP 
                    COMMUNITY and the value labeled 'Trap Community:' in 
                    the SERVER INTERNET SNMP CHARACTERISTICS display."
                ::= { snmpAgent 3 }
            

            
            
            
            
            
            
            snmpAgentGetClientNumber OBJECT-TYPE
                SYNTAX INTEGER
                ACCESS read-only
                STATUS mandatory
                DESCRIPTION
                    "The number of client source addresses allowed to 
                    perform get-requests or get-next requests to this 
                    agent.  If the value is 0, the agent does not check 
                    source address for these operations.  Corresponds 
                    indirectly to the values labeled 'Get Client n:' in 
                    the SERVER INTERNET SNMP CHARACTERISTICS display."
                ::= { snmpAgent 4 }
            
            snmpAgentSetClientNumber OBJECT-TYPE
                SYNTAX INTEGER
                ACCESS read-only
                STATUS mandatory
                DESCRIPTION
                    "The number of client source addresses allowed to 
                    perform set-requests to this agent.  If the value is 
                    0, the agent does not check source address for these 
                    operations.  Corresponds indirectly to the values 
                    labeled 'Set Client n:' in the SERVER INTERNET SNMP 
                    CHARACTERISTICS display."
                ::= { snmpAgent 5 }
            
            snmpAgentTrapClientNumber OBJECT-TYPE
                SYNTAX INTEGER
                ACCESS read-only
                STATUS mandatory
                DESCRIPTION
                    "The number of client source addresses to which this 
                    agent sends traps.  If the value is 0, the agent 
                    does not perform this operation.  Corresponds 
                    indirectly to the values labeled 'Trap Client n:' in 
                    the SERVER INTERNET SNMP CHARACTERISTICS display."
                ::= { snmpAgent 6 }









            
            
            
            
            
            
            -- the Get Client table
            
            getClientTable OBJECT-TYPE
                SYNTAX SEQUENCE OF GetClientEntry
                ACCESS not-accessible
                STATUS mandatory
                DESCRIPTION
                    "A list of get client entries.  The number of 
                    entries is given by the value of 
                    snmpAgentGetClientNumber."
                ::= { snmpAgent 7 }
            
            getClientEntry OBJECT-TYPE
                SYNTAX GetClientEntry
                ACCESS not-accessible
                STATUS mandatory
                DESCRIPTION
                    "Parameter values for a get client."
                INDEX { getClientIndex }
                ::= { getClientTable 1 }
            
            GetClientEntry ::=
                SEQUENCE {
                    getClientIndex
                        INTEGER,
                    getClientEntryStatus
                        INTEGER,
                    getClientAddressType
                        INTEGER,
                    getClientAddress
                        OCTET STRING
                }
            
            getClientIndex OBJECT-TYPE
                SYNTAX INTEGER
                ACCESS read-only
                STATUS mandatory
                DESCRIPTION
                    "Identification of a get client entry.  Corresponds 
                    directly to the number in the label 'Get Client n:' 
                    in the SERVER INTERNET SNMP CHARACTERISTICS 
                    display."
                ::= { getClientEntry 1 }
            
            getClientEntryStatus OBJECT-TYPE
                SYNTAX INTEGER { invalid(1), valid(2) }

            
            
            
            
            
            
                ACCESS read-write
                STATUS mandatory
                DESCRIPTION
                    "Status of this entry.  Setting the value to 
                    'invalid' invalidates the entry.  It is an 
                    implementation-specific matter as to whether the 
                    agent removes an invalidated entry from the table."
                DEFVAL { valid }
                ::= { getClientEntry 2 }
            
            getClientAddressType OBJECT-TYPE
                SYNTAX AddressType
                ACCESS read-write
                STATUS mandatory
                DESCRIPTION
                    "The type of network address contained in 
                    getClientAddress.  'unknown' means no address has 
                    been defined.  'other' means no other type value 
                    applies.  'ip' is an Internet IP address.  
                    'ethernet' is an 802.3 MAC address.  If 
                    getClientAddressType does not accompany 
                    getClientAddress in a set request, the default type 
                    is 'ip'.  Corresponds indirectly to the address 
                    value labeled 'Get Client n:' in the SERVER INTERNET 
                    SNMP CHARACTERISTICS display."
                DEFVAL { unknown }
                ::= { getClientEntry 3 }
            
            getClientAddress OBJECT-TYPE
                SYNTAX OCTET STRING
                ACCESS read-write
                STATUS mandatory
                DESCRIPTION
                    "The client's network address.  If 
                    getClientAddressType does not accompany 
                    getClientAddress in a set request, the default type 
                    is 'ip'.  Corresponds directly to the address value 
                    labeled 'Get Client n:' in the SERVER INTERNET SNMP 
                    CHARACTERISTICS display."
                DEFVAL { null }  -- 'null' indicates zero length
                ::= { getClientEntry 4 }





            
            
            
            
            
            
            -- the Set Client table
            
            setClientTable OBJECT-TYPE
                SYNTAX SEQUENCE OF SetClientEntry
                ACCESS not-accessible
                STATUS mandatory
                DESCRIPTION
                    "A list of set client entries.  The number of 
                    entries is given by the value of 
                    snmpAgentSetClientNumber."
                ::= { snmpAgent 8 }
            
            setClientEntry OBJECT-TYPE
                SYNTAX SetClientEntry
                ACCESS not-accessible
                STATUS mandatory
                DESCRIPTION
                    "Parameter values for a set client."
                INDEX { setClientIndex }
                ::= { setClientTable 1 }
            
            SetClientEntry ::=
                SEQUENCE {
                    setClientIndex
                        INTEGER,
                    setClientEntryStatus
                        INTEGER,
                    setClientAddressType
                        INTEGER,
                    setClientAddress
                        OCTET STRING
                }
            
            setClientIndex OBJECT-TYPE
                SYNTAX INTEGER
                ACCESS read-only
                STATUS mandatory
                DESCRIPTION
                    "Identification of a set client entry.  Corresponds 
                    directly to the number in the label 'Set Client n:' 
                    in the SERVER INTERNET SNMP CHARACTERISTICS 
                    display."
                ::= { setClientEntry 1 }
            
            setClientEntryStatus OBJECT-TYPE
                SYNTAX INTEGER { invalid(1), valid(2) }

            
            
            
            
            
            
                ACCESS read-write
                STATUS mandatory
                DESCRIPTION
                    "Status of this entry.  Setting the value to 
                    'invalid' invalidates the entry.  It is an 
                    implementation-specific matter as to whether the 
                    agent removes an invalidated entry from the table."
                DEFVAL { valid }
                ::= { setClientEntry 2 }
            
            setClientAddressType OBJECT-TYPE
                SYNTAX AddressType
                ACCESS read-write
                STATUS mandatory
                DESCRIPTION
                    "The type of network address contained in 
                    setClientAddress.  'unknown' means no address has 
                    been defined.  'other' means no other type value 
                    applies.  'ip' is an Internet IP address.  
                    'ethernet' is an 802.3 MAC address.  If 
                    setClientAddressType does not accompany 
                    setClientAddress in a set request, the default type 
                    is 'ip'.  Corresponds indirectly to the address 
                    value labeled 'Set Client n:' in the SERVER INTERNET 
                    SNMP CHARACTERISTICS display."
                DEFVAL { unknown }
                ::= { setClientEntry 3 }
            
            setClientAddress OBJECT-TYPE
                SYNTAX OCTET STRING
                ACCESS read-write
                STATUS mandatory
                DESCRIPTION
                    "The client's network address.  When setting this 
                    value, the requester must supply 
                    setClientAddressType.  If setClientAddressType does 
                    not accompany setClientAddress in a set request, the 
                    default type is 'ip'.  Corresponds directly to the 
                    address value labeled 'Set Client n:' in the SERVER 
                    INTERNET SNMP CHARACTERISTICS display."
                DEFVAL { null }  -- 'null' indicates zero length
                ::= { setClientEntry 4 }




            
            
            
            
            
            
            -- the Trap Client table
            
            trapClientTable OBJECT-TYPE
                SYNTAX SEQUENCE OF TrapClientEntry
                ACCESS not-accessible
                STATUS mandatory
                DESCRIPTION
                    "A list of trap client entries.  The number of 
                    entries is given by the value of 
                    snmpAgentTrapClientNumber."
                ::= { snmpAgent 9 }
            
            trapClientEntry OBJECT-TYPE
                SYNTAX TrapClientEntry
                ACCESS not-accessible
                STATUS mandatory
                DESCRIPTION
                    "Parameter values for a trap client."
                INDEX { trapClientIndex }
                ::= { trapClientTable 1 }
            
            TrapClientEntry ::=
                SEQUENCE {
                    trapClientIndex
                        INTEGER,
                    trapClientEntryStatus
                        INTEGER,
                    trapClientAddressType
                        INTEGER,
                    trapClientAddress
                        OCTET STRING
                }
            
            trapClientIndex OBJECT-TYPE
                SYNTAX INTEGER
                ACCESS read-only
                STATUS mandatory
                DESCRIPTION
                    "Identification of a trap client entry.  Corresponds 
                    directly to the number in the label 'Trap Client n:' 
                    in the SERVER INTERNET SNMP CHARACTERISTICS 
                    display."
                ::= { trapClientEntry 1 }
            
            trapClientEntryStatus OBJECT-TYPE
                SYNTAX INTEGER { invalid(1), valid(2) }

            
            
            
            
            
            
                ACCESS read-write
                STATUS mandatory
                DESCRIPTION
                    "Status of this entry.  Setting the value to 
                    'invalid' invalidates the entry.  It is an 
                    implementation-specific matter as to whether the 
                    agent removes an invalidated entry from the table."
                DEFVAL { valid }
                ::= { trapClientEntry 2 }
            
            trapClientAddressType OBJECT-TYPE
                SYNTAX AddressType
                ACCESS read-write
                STATUS mandatory
                DESCRIPTION
                    "The type of network address contained in 
                    trapClientAddress.  'unknown' means no address has 
                    been defined.  'other' means no other type value 
                    applies.  'ip' is an Internet IP address.  
                    'ethernet' is an 802.3 MAC address.  If 
                    trapClientAddressType does not accompany 
                    trapClientAddress in a set request, the default type 
                    is 'ip'.  Corresponds indirectly to the address 
                    value labeled 'Trap Client n:' in the SERVER 
                    INTERNET SNMP CHARACTERISTICS display."
                DEFVAL { unknown }
                ::= { trapClientEntry 3 }
            
            trapClientAddress OBJECT-TYPE
                SYNTAX OCTET STRING
                ACCESS read-write
                STATUS mandatory
                DESCRIPTION
                    "The client's network address.  When setting this 
                    value, the requester must supply 
                    trapClientAddressType.  If trapClientAddressType 
                    does not accompany trapClientAddress in a set 
                    request, the default type is 'ip'.  Corresponds 
                    directly to the address value labeled 'Trap Client 
                    n:' in the SERVER INTERNET SNMP CHARACTERISTICS 
                    display."
                DEFVAL { null }  -- 'null' indicates zero length
                ::= { trapClientEntry 4 }



            
            
            
            
            
            
            -- the Domain Resolver group
            
            -- Implementation of this group is mandatory for all Xyplex
            -- systems that implement Domain name resolution
            
            domainResolverSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { domainResolver 1 }
            
            domainResolverAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { domainResolver 2 }
            
            domainResolverAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { domainResolver 3 }
            

            
            
            
            
            
            
            domainResolverTtl OBJECT-TYPE
                SYNTAX INTEGER (0..168)
                ACCESS read-write
                STATUS mandatory
                DESCRIPTION
                    "The number of hours to keep received Domain 
                    information.  Corresponds directly to SERVER 
                    INTERNET DOMAIN TTL and the value labeled ' Domain 
                    TTL:' in the SERVER INTERNET CHARACTERISTICS 
                    display."
                ::= { domainResolver 4 }
            
            domainResolverNameNumber OBJECT-TYPE
                SYNTAX INTEGER
                ACCESS read-only
                STATUS mandatory
                DESCRIPTION
                    "The number of Domain name mappings in this system's 
                    name cache."
                ::= { domainResolver 5 }


























            
            
            
            
            
            
            -- the Name table
            
            nameTable OBJECT-TYPE
                SYNTAX SEQUENCE OF NameEntry
                ACCESS not-accessible
                STATUS mandatory
                DESCRIPTION
                    "A list of Domain name entries.  The number of 
                    entries is given by the value of 
                    domainResolverNameNumber."
                ::= { domainResolver 6 }
            
            nameEntry OBJECT-TYPE
                SYNTAX NameEntry
                ACCESS not-accessible
                STATUS mandatory
                DESCRIPTION
                    "Parameter values for a Domain name."
                INDEX { nameName, nameAddress }
                ::= { nameTable 1 }
            
            NameEntry ::=
                SEQUENCE {
                    nameName
                        DisplayString,
                    nameAddress
                        IpAddress,
                    nameStatus
                        INTEGER,
                    nameSource
                        INTEGER,
                    nameTtl
                        INTEGER
                }
            
            nameName OBJECT-TYPE
                SYNTAX DisplayString (SIZE (1..50))
                ACCESS read-only
                STATUS mandatory
                DESCRIPTION
                    "A fully qualified domain name.  Corresponds 
                    directly to the value labeled 'Domain Name' in the 
                    DOMAIN display."
                ::= { nameEntry 1 }
            
            nameAddress OBJECT-TYPE

            
            
            
            
            
            
                SYNTAX IpAddress
                ACCESS read-write
                STATUS mandatory
                DESCRIPTION
                    "An Internet address corresponding to the Domain 
                    name.  Corresponds directly to the value labeled 
                    'Internet Address' in the DOMAIN display."
                ::= { nameEntry 2 }
            
            nameStatus OBJECT-TYPE
                SYNTAX INTEGER { invalid(1), valid(2) }
                ACCESS read-write
                STATUS mandatory
                DESCRIPTION
                    "The status of the entry.  Set to 'invalid' to 
                    remove the entry, which corresponds directly to the 
                    PURGE DOMAIN command.  Actual removal of the entry 
                    is implementation specific."
                ::= { nameEntry 3 }
            
            nameSource OBJECT-TYPE
                SYNTAX INTEGER { manager(1), primary(2), secondary(3) }
                ACCESS read-only
                STATUS mandatory
                DESCRIPTION
                    "Source of this entry.  The value meanings are:
            
                    local       defined by manager (LOCAL)
                    primary     obtained from a primary name server
                    secondary   obtained from a secondary name server
            
                    Corresponds directly to the value labeled 'Source' 
                    in the DOMAIN display."
                ::= { nameEntry 4 }
            
            nameTtl OBJECT-TYPE
                SYNTAX INTEGER
                ACCESS read-only
                STATUS mandatory
                DESCRIPTION
                    "The number of minutes remaining in the entry's time 
                    to live.  Corresponds directly to the value labeled 
                    'TTL' in the DOMAIN display."
                DEFVAL { domainResolverTtl }
                ::= { nameEntry 5 }

            
            
            
            
            
            
            -- the SLIP group
            
            -- Implementation of this group is mandatory for all Xyplex
            -- systems that implement SLIP ports
            
            slipTable OBJECT-TYPE
                SYNTAX SEQUENCE OF SlipEntry
                ACCESS not-accessible
                STATUS mandatory
                DESCRIPTION
                    "A list of SLIP character port entries."
                ::= { slip 1 }
            
            slipEntry OBJECT-TYPE
                SYNTAX SlipEntry
                ACCESS not-accessible
                STATUS mandatory
                DESCRIPTION
                    "Parameter values for a SLIP port."
                INDEX { slipIndex }
                ::= { slipTable 1 }
            
            SlipEntry ::=
                SEQUENCE {
                    slipIndex
                        INTEGER,
                    slipState
                        INTEGER,
                    slipLocalAddress
                        IpAddress,
                    slipRemoteAddress
                        IpAddress,
                    slipMask
                        IpAddress,
                    slipPortPacketsReceived
                        Counter,
                    slipPortPacketsSent
                        Counter,
                    slipPortPacketsDiscarded
                        Counter,
                    slipPortPacketLengthErrors
                        Counter,
                    slipPortPacketChecksumErrors
                        Counter,
                    slipNetworkPacketsReceived
                        Counter,

            
            
            
            
            
            
                    slipNetworkPacketsSent
                        Counter,
                    slipNetworkPacketsDiscarded
                        Counter
                }
            
            slipIndex OBJECT-TYPE
                SYNTAX INTEGER
                ACCESS read-only
                STATUS mandatory
                DESCRIPTION
                    "An index value that uniquely identifies a port that 
                    can run SLIP.  The port identified by a particular 
                    value of this index is the same port as identified 
                    by charPortIndex in the Proposed Standard Internet 
                    Character MIB."
                ::= { slipEntry 1 }
            
            slipState OBJECT-TYPE
                SYNTAX INTEGER { off(1), on(2) }
                ACCESS read-write
                STATUS mandatory
                DESCRIPTION
                    "A control indicating whether SLIP is in operation 
                    on the port.  Corresponds directly to PORT INTERNET 
                    SLIP and the value labeled 'SLIP' in the PORT 
                    CHARACTERISTICS display."
                ::= { slipEntry 2 }
            
            slipLocalAddress OBJECT-TYPE
                SYNTAX IpAddress
                ACCESS read-write
                STATUS mandatory
                DESCRIPTION
                    "The IP address assigned to the port.  Corresponds 
                    directly to PORT SLIP ADDRESS and the value labeled 
                    'SLIP Address:' in the PORT ALTERNATE 
                    CHARACTERISTICS display."
                ::= { slipEntry 3 }
            
            slipRemoteAddress OBJECT-TYPE
                SYNTAX IpAddress
                ACCESS read-write
                STATUS mandatory
                DESCRIPTION
                    "The IP address of the remote system attached to the 

            
            
            
            
            
            
                            port.  Corresponds directly to PORT SLIP REMOTE and 
                    the value labeled 'Remote SLIP Address:' in the PORT 
                    ALTERNATE CHARACTERISTICS display."
                ::= { slipEntry 4 }
            
            slipMask OBJECT-TYPE
                SYNTAX IpAddress
                ACCESS read-write
                STATUS mandatory
                DESCRIPTION
                    "The subnet mask to use for SLIP operation on the 
                    port.  Corresponds directly to PORT SLIP MASK and 
                    the value labeled 'SLIP Mask:' in the PORT ALTERNATE 
                    CHARACTERISTICS display."
                ::= { slipEntry 5 }
            
            slipPortPacketsReceived OBJECT-TYPE
                SYNTAX Counter
                ACCESS read-only
                STATUS mandatory
                DESCRIPTION
                    "The number of SLIP packets received from the port.  
                    Corresponds directly to the value labeled 'Serial 
                    Packets Received:' in the PORT COUNTERS display."
                ::= { slipEntry 6 }
            
            slipPortPacketsSent OBJECT-TYPE
                SYNTAX Counter
                ACCESS read-only
                STATUS mandatory
                DESCRIPTION
                    "The number of SLIP packets sent to the port.  
                    Corresponds directly to the value labeled 'Serial 
                    Packets Sent:' in the PORT COUNTERS display."
                ::= { slipEntry 7 }
            
            slipPortPacketsDiscarded OBJECT-TYPE
                SYNTAX Counter
                ACCESS read-only
                STATUS mandatory
                DESCRIPTION
                    "The number of SLIP packets received from the port 
                    and discarded.  Corresponds directly to the value 
                    labeled 'Serial Packets Discarded:' in the PORT 
                    COUNTERS display."
                ::= { slipEntry 8 }

            
            
            
            
            
            
            
            slipPortPacketLengthErrors OBJECT-TYPE
                SYNTAX Counter
                ACCESS read-only
                STATUS mandatory
                DESCRIPTION
                    "The number of SLIP packets received from the port 
                    with an incorrect number of bytes.  Corresponds 
                    directly to the value labeled 'Serial Packet Length 
                    Errors:' in the PORT COUNTERS display."
                ::= { slipEntry 9 }
            
            slipPortPacketChecksumErrors OBJECT-TYPE
                SYNTAX Counter
                ACCESS read-only
                STATUS mandatory
                DESCRIPTION
                    "The number of SLIP packets received from the port 
                    with an invalid checksum.  Corresponds directly to 
                    the value labeled 'Serial Packet Checksum Errors:' 
                    in the PORT COUNTERS display."
                ::= { slipEntry 10 }
            
            slipNetworkPacketsReceived OBJECT-TYPE
                SYNTAX Counter
                ACCESS read-only
                STATUS mandatory
                DESCRIPTION
                    "The number of SLIP packets received from the 
                    network for this port.  Corresponds directly to the 
                    value labeled 'Network Packets Received:' in the 
                    PORT COUNTERS display."
                ::= { slipEntry 11 }
            
            slipNetworkPacketsSent OBJECT-TYPE
                SYNTAX Counter
                ACCESS read-only
                STATUS mandatory
                DESCRIPTION
                    "The number of SLIP packets sent to the network from 
                    this port.  Corresponds directly to the value 
                    labeled 'Network Packets Sent:' in the PORT COUNTERS 
                    display."
                ::= { slipEntry 12 }
            
            slipNetworkPacketsDiscarded OBJECT-TYPE

            
            
            
            
            
            
                SYNTAX Counter
                ACCESS read-only
                STATUS mandatory
                DESCRIPTION
                    "The number of SLIP packets received from the 
                    network for this port and discarded.  Corresponds 
                    directly to the value labeled 'Network Packets 
                    Discarded:' in the PORT COUNTERS display."
                ::= { slipEntry 13 }





































            
            
            
            
            
            
            -- the Telnet group
            
            -- Implementation of this group is mandatory for all Xyplex
            -- systems that implement Telnet
            
            -- the Telnet Character Port table
            
            -- Ports in this table are either serial or parallel
            
            telnetPortTable OBJECT-TYPE
                SYNTAX SEQUENCE OF TelnetPortEntry
                ACCESS not-accessible
                STATUS mandatory
                DESCRIPTION
                    "A list of Telnet character port entries."
                ::= { telnet 1 }
            
            telnetPortEntry OBJECT-TYPE
                SYNTAX TelnetPortEntry
                ACCESS not-accessible
                STATUS mandatory
                DESCRIPTION
                    "Telnet parameter values for a character port."
                INDEX { telnetPortIndex }
                ::= { telnetPortTable 1 }
            
            TelnetPortEntry ::=
                SEQUENCE {
                    telnetPortIndex
                        INTEGER,
                    telnetPortIncomingTcpPort
                        INTEGER,
                    telnetPortOutgoingTcpPort
                        INTEGER,
                    telnetPortNewlineTranslation
                        INTEGER,
                    telnetPortTerminalType
                        DisplayString,
                    telnetPortEorReflection
                        INTEGER,
                    telnetPortBinaryMode
                        INTEGER
                }
            
            telnetPortIndex OBJECT-TYPE
                SYNTAX INTEGER

            
            
            
            
            
            
                ACCESS read-only
                STATUS mandatory
                DESCRIPTION
                    "An index value that uniquely identifies a port.  
                    The port identified by a particular value of this 
                    index is the same port as identified by 
                    charPortIndex in the Proposed Standard Internet 
                    Character MIB."
                ::= { telnetPortEntry 1 }
            
            telnetPortIncomingTcpPort OBJECT-TYPE
                SYNTAX INTEGER (1..32767)
                ACCESS read-write
                STATUS mandatory
                DESCRIPTION
                    "The TCP port number offered for incoming 
                    connections to this character port.  Corresponds 
                    directly to PORT TELNET REMOTE PORT and the value 
                    labeled 'Remote Port:' in the PORT TELNET 
                    CHARACTERISTICS display."
                ::= { telnetPortEntry 2 }
            
            telnetPortOutgoingTcpPort OBJECT-TYPE
                SYNTAX INTEGER
                ACCESS read-only
                STATUS mandatory
                DESCRIPTION
                    "The TCP port number used by default for outgoing 
                    connections from this character port.  Corresponds 
                    directly to PORT TELNET DEFAULT PORT and the value 
                    labeled 'Default Port:' in the PORT TELNET 
                    CHARACTERISTICS display."
                ::= { telnetPortEntry 3 }
            
            telnetPortNewlineTranslation OBJECT-TYPE
                SYNTAX INTEGER { none(1), cr(2), crNull(3), crLf(4) }
                ACCESS read-write
                STATUS mandatory
                DESCRIPTION
                    "Translation to apply to newline sequences (CR/NULL 
                    or CR/LF) received from the network, before sending 
                    the newline to the character port.  The value 
                    indicates the sequence sent to the character port, 
                    with 'none' meaning no translation.  Corresponds 
                    directly to PORT TELNET NEWLINE FILTERING and the 
                    value labeled 'Newline Filtering:' in the PORT 

            
            
            
            
            
            
                            TELNET CHARACTERISTICS display."
                ::= { telnetPortEntry 4 }
            
            telnetPortTerminalType OBJECT-TYPE
                SYNTAX DisplayString (SIZE (1..20))
                ACCESS read-write
                STATUS mandatory
                DESCRIPTION
                    "The terminal type character string for Telnet 
                    negotiations.  Corresponds directly to PORT TELNET 
                    TERMINALTYPE and the value labeled 'TerminalType:' 
                    in the PORT TELNET CHARACTERISTICS display."
                ::= { telnetPortEntry 5 }
            
            telnetPortEorReflection OBJECT-TYPE
                SYNTAX INTEGER { disabled(1), enabled(2) }
                ACCESS read-write
                STATUS mandatory
                DESCRIPTION
                    "Control for end-of-record handshake.  Corresponds 
                    directly to PORT TELNET EOR REFLECTION and the value 
                    labeled 'EOR Reflection:' in the PORT TELNET 
                    CHARACTERISTICS display."
                ::= { telnetPortEntry 6 }
            
            telnetPortBinaryMode OBJECT-TYPE
                SYNTAX INTEGER { flowControl(1), complete(2),
                                 disabled(3) }
                ACCESS read-write
                STATUS mandatory
                DESCRIPTION
                    "Control for operation of Telnet binary mode.  The 
                    value meanings are:
            
                    disabled      refuse binary mode negotiation
                                  (INTERACTIVE)
                    flowControl   pass all but XON and XOFF (PASTHRU)
                    complete      pass all characters (PASSALL)
            
                    Corresponds directly to PORT TELNET BINARY SESSION 
                    MODE and the value labeled 'Binary Session Mode:' in 
                    the PORT TELNET CHARACTERISTICS display."
                ::= { telnetPortEntry 7 }



            
            
            
            
            
            
            -- the Telnet Serial Character Port table
            
            telnetSerialPortTable OBJECT-TYPE
                SYNTAX SEQUENCE OF TelnetSerialPortEntry
                ACCESS not-accessible
                STATUS mandatory
                DESCRIPTION
                    "A list of Telnet character port entries."
                ::= { telnet 2 }
            
            telnetSerialPortEntry OBJECT-TYPE
                SYNTAX TelnetSerialPortEntry
                ACCESS not-accessible
                STATUS mandatory
                DESCRIPTION
                    "Telnet parameter values for a character port."
                INDEX { telnetSerialPortIndex }
                ::= { telnetSerialPortTable 1 }
            
            TelnetSerialPortEntry ::=
                SEQUENCE {
                    telnetSerialPortIndex
                        INTEGER,
                    telnetSerialPortOptionDisplay
                        INTEGER,
                    telnetSerialPortCsiEscape
                        INTEGER,
                    telnetSerialPortEchoMode
                        INTEGER,
                    telnetSerialPortNewlineMode
                        INTEGER,
                    telnetSerialPortTransmitMode
                        INTEGER,
                    telnetSerialPortTransmitCharacterTimes
                        INTEGER,
                    telnetSerialPortAbortOutputCharacter
                        INTEGER,
                    telnetSerialPortAttentionCharacter
                        INTEGER,
                    telnetSerialPortEraseKeyCharacter
                        INTEGER,
                    telnetSerialPortEraseLineCharacter
                        INTEGER,
                    telnetSerialPortInterruptCharacter
                        INTEGER,
                    telnetSerialPortQueryCharacter

            
            
            
            
            
            
                        INTEGER,
                    telnetSerialPortSynchronizeCharacter
                        INTEGER
                }
            
            telnetSerialPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetSerialPortEntry 1 }
            
            telnetSerialPortOptionDisplay OBJECT-TYPE
                SYNTAX INTEGER { disabled(1), enabled(2) }
                ACCESS read-write
                STATUS mandatory
                DESCRIPTION
                    "Control for display of Telnet option negotiations.  
                    Corresponds directly to PORT TELNET OPTION DISPLAY 
                    and the value labeled 'Option Display:' in the PORT 
                    TELNET CHARACTERISTICS display."
                ::= { telnetSerialPortEntry 2 }
            
            telnetSerialPortCsiEscape OBJECT-TYPE
                SYNTAX INTEGER { disabled(1), enabled(2) }
                ACCESS read-write
                STATUS mandatory
                DESCRIPTION
                    "Control for translation of 8-bit escape sequences 
                    received from the character port to 7-bit 
                    equivalents before transmission to the remote 
                    partner.  Corresponds directly to PORT TELNET CSI 
                    ESCAPE and the value labeled 'CSI Escape:' in the 
                    PORT TELNET CHARACTERISTICS display."
                ::= { telnetSerialPortEntry 3 }
            
            telnetSerialPortEchoMode OBJECT-TYPE
                SYNTAX INTEGER { local(1), remote(2) }
                ACCESS read-write
                STATUS mandatory
                DESCRIPTION

            
            
            
            
            
            
                    "Control for who echoes characters that come from 
                    the character port.  The value meanings are:
            
                    local    terminal server echoes locally
                    remote   remote system echoes
            
                    Corresponds directly to PORT TELNET ECHO MODE and 
                    the value labeled 'Echo Mode:' in the PORT TELNET 
                    CHARACTERISTICS display."
                ::= { telnetSerialPortEntry 4 }
            
            telnetSerialPortNewlineMode OBJECT-TYPE
                SYNTAX INTEGER { crNull(1), crLf(2), verbatim(3) }
                ACCESS read-write
                STATUS mandatory
                DESCRIPTION
                    "Translation to apply to newline (carriage return) 
                    received from the character port, before sending the 
                    newline to the remote partner.  The correspondence 
                    to command keywords is 'crNull' to NULL, 'crLF' to 
                    LINEFEED, and 'verbatim' to NOTHING (that is, no 
                    translation).  Corresponds directly to PORT TELNET 
                    NEWLINE and the value labeled 'Newline:' in the PORT 
                    TELNET CHARACTERISTICS display."
                ::= { telnetSerialPortEntry 5 }
            
            telnetSerialPortTransmitMode OBJECT-TYPE
                SYNTAX INTEGER { immediate(1), buffered(2), timed(3) }
                ACCESS read-write
                STATUS mandatory
                DESCRIPTION
                    "Criterion for deciding to send to the remote 
                    partner characters received from the character port.  
                    Corresponds directly to PORT TELNET TRANSMIT and the 
                    value labeled 'Transmit:' in the PORT TELNET 
                    CHARACTERISTICS display."
                ::= { telnetSerialPortEntry 6 }
            
            telnetSerialPortTransmitCharacterTimes OBJECT-TYPE
                SYNTAX INTEGER (1..255)
                ACCESS read-write
                STATUS mandatory
                DESCRIPTION
                    "Number of character times to wait before 
                    transmitting when telnetSerialPortTransmitMode value 
                    is 'timed'.  Corresponds directly to PORT TELNET 

            
            
            
            
            
            
                            TRANSMIT IDLETIME and the value labeled 'Transmit:  
                    Idle Time -' in the PORT TELNET CHARACTERISTICS 
                    display."
                ::= { telnetSerialPortEntry 7 }
            
            telnetSerialPortAbortOutputCharacter OBJECT-TYPE
                SYNTAX INTEGER (0..255)
                ACCESS read-write
                STATUS mandatory
                DESCRIPTION
                    "Character input from the character port to cause 
                    aborting output.  The value 0 indicates no character 
                    has this effect.  Corresponds directly to PORT 
                    TELNET ABORT OUTPUT and the value labeled 'Abort 
                    Output Character:' in the PORT TELNET 
                    CHARACTERISTICS display."
                ::= { telnetSerialPortEntry 8 }
            
            telnetSerialPortAttentionCharacter OBJECT-TYPE
                SYNTAX INTEGER (0..255)
                ACCESS read-write
                STATUS mandatory
                DESCRIPTION
                    "Character input from the character port to cause an 
                    attention notification to the remote partner.  The 
                    value 0 indicates no character has this effect.  
                    Corresponds directly to PORT TELNET ATTENTION and 
                    the value labeled 'Attention Character:' in the PORT 
                    TELNET CHARACTERISTICS display."
                ::= { telnetSerialPortEntry 9 }
            
            telnetSerialPortEraseKeyCharacter OBJECT-TYPE
                SYNTAX INTEGER (0..255)
                ACCESS read-write
                STATUS mandatory
                DESCRIPTION
                    "Character input from the character port to cause 
                    erasure of the previous input character.  The value 
                    0 indicates no character has this effect.  
                    Corresponds directly to PORT TELNET ERASE CHARACTER 
                    and the value labeled 'Erase Keystroke Character:' 
                    in the PORT TELNET CHARACTERISTICS display."
                ::= { telnetSerialPortEntry 10 }
            
            telnetSerialPortEraseLineCharacter OBJECT-TYPE
                SYNTAX INTEGER (0..255)

            
            
            
            
            
            
                ACCESS read-write
                STATUS mandatory
                DESCRIPTION
                    "Character input from the character port to cause 
                    erasure of the previous line of input.  The value 0 
                    indicates no character has this effect.  Corresponds 
                    directly to PORT TELNET ERASE LINE and the value 
                    labeled 'Erase Line Character:' in the PORT TELNET 
                    CHARACTERISTICS display."
                ::= { telnetSerialPortEntry 11 }
            
            telnetSerialPortInterruptCharacter OBJECT-TYPE
                SYNTAX INTEGER (0..255)
                ACCESS read-write
                STATUS mandatory
                DESCRIPTION
                    "Character input from the character port to cause 
                    sending an interrupt notification to the remote 
                    partner.  The value 0 indicates no character has 
                    this effect.  Corresponds directly to PORT TELNET 
                    INTERRUPT and the value labeled 'Interrupt 
                    Character:' in the PORT TELNET CHARACTERISTICS 
                    display."
                ::= { telnetSerialPortEntry 12 }
            
            telnetSerialPortQueryCharacter OBJECT-TYPE
                SYNTAX INTEGER (0..255)
                ACCESS read-write
                STATUS mandatory
                DESCRIPTION
                    "Character input from the character port to cause 
                    sending a status query to the remote partner.  The 
                    value 0 indicates no character has this effect.  
                    Corresponds directly to PORT TELNET QUERY and the 
                    value labeled 'Query Character:' in the PORT TELNET 
                    CHARACTERISTICS display."
                ::= { telnetSerialPortEntry 13 }
            
            telnetSerialPortSynchronizeCharacter OBJECT-TYPE
                SYNTAX INTEGER (0..255)
                ACCESS read-write
                STATUS mandatory
                DESCRIPTION
                    "Character input from the character port to cause 
                    sending a synchronization attempt to the remote 
                    partner.  The value 0 indicates no character has 

            
            
            
            
            
            
                            this effect.  Corresponds directly to PORT TELNET 
                    SYNCHRONIZE and the value labeled 'Synchronize 
                    Character:' in the PORT TELNET CHARACTERISTICS 
                    display."
                ::= { telnetSerialPortEntry 14 }









































            
            
            
            
            
            
            -- the tn3270 group
            
            -- Implementation of this group is mandatory for all Xyplex
            -- systems that implement tn3270
            
            tn3270DeviceNumber OBJECT-TYPE
                SYNTAX INTEGER
                ACCESS read-only
                STATUS mandatory
                DESCRIPTION
                    "The number of entries in the tn3270 Device table."
                ::= { tn3270 1 }
            
            tn3270LanguageNumber OBJECT-TYPE
                SYNTAX INTEGER
                ACCESS read-only
                STATUS mandatory
                DESCRIPTION
                    "The number of entries in the tn3270 Language 
                    table."
                ::= { tn3270 2 }
            
            tn3270PortKeymapStatus OBJECT-TYPE
                SYNTAX INTEGER { disabled(1), enabled(2) }
                ACCESS read-write
                STATUS mandatory
                DESCRIPTION
                    "Control for individual ports to create their own 
                    keymaps.  Corresponds directly to SERVER TN3270 PORT 
                    KEYMAPS and the value labeled 'Port Keymaps:' in the 
                    SERVER TN3270 display."
                ::= { tn3270 3 }














            
            
            
            
            
            
            -- The tn3270 Device table
            
            tn3270DeviceTable OBJECT-TYPE
                SYNTAX SEQUENCE OF Tn3270DeviceEntry
                ACCESS not-accessible
                STATUS mandatory
                DESCRIPTION
                    "A list of tn3270 terminal device entries."
                ::= { tn3270 4 }
            
            tn3270DeviceEntry OBJECT-TYPE
                SYNTAX Tn3270DeviceEntry
                ACCESS not-accessible
                STATUS mandatory
                DESCRIPTION
                    "Tn3270 parameter values for a terminal device 
                    entry."
                INDEX { tn3270DeviceName }
                ::= { tn3270DeviceTable 1 }
            
            Tn3270DeviceEntry ::=
                SEQUENCE {
                    tn3270DeviceName
                        DisplayString,
                    tn3270DeviceStatus
                        INTEGER,
                    tn3270DeviceType
                        DisplayString,
                    tn3270Device3278Model
                        INTEGER,
                    tn3270DeviceKeyNumber
                        INTEGER,
                    tn3270DeviceScreenNumber
                        INTEGER
                }
            
            tn3270DeviceName OBJECT-TYPE
                SYNTAX DisplayString (SIZE (1..8))
                ACCESS read-write
                STATUS mandatory
                DESCRIPTION
                    "The name of a generic terminal device.  Corresponds 
                    directly to SERVER TN3270 DEVICE and the value 
                    labeled 'Device Name:' in the SERVER TN3270 DEVICE 
                    display."
                ::= { tn3270DeviceEntry 1 }

            
            
            
            
            
            
            
            tn3270DeviceStatus OBJECT-TYPE
                SYNTAX INTEGER { invalid(1), valid(2) }
                ACCESS read-write
                STATUS mandatory
                DESCRIPTION
                    "Status of this entry.  Setting the value to 
                    'invalid' invalidates the entry, corresponding 
                    directly to the PURGE SERVER TN3270 DEVICE command.  
                    It is an implementation-specific matter as to 
                    whether the agent removes an invalidated entry from 
                    the table."
                DEFVAL { valid }
                ::= { tn3270DeviceEntry 2 }
            
            tn3270DeviceType OBJECT-TYPE
                SYNTAX DisplayString (SIZE (1..20))
                ACCESS read-write
                STATUS mandatory
                DESCRIPTION
                    "The terminal type character string for use when 
                    tn3270DeviceTn3270Type is insufficient.  Corresponds 
                    directly to SERVER TN3270 DEVICE TERMINALTYPE and 
                    the value labeled 'TerminalType:' in the SERVER 
                    TN3270 DEVICE display."
                ::= { tn3270DeviceEntry 3 }
            
            tn3270Device3278Model OBJECT-TYPE
                SYNTAX INTEGER { model2(1), model5(2) }
                ACCESS read-write
                STATUS mandatory
                DESCRIPTION
                    "The 3278 model for the device.  Corresponds 
                    directly to SERVER TN3270 DEVICE TN3278Model and the 
                    value labeled 'Tn3278Model:' in the SERVER TN3270 
                    DEVICE display."
                ::= { tn3270DeviceEntry 4 }
            
            tn3270DeviceKeyNumber OBJECT-TYPE
                SYNTAX INTEGER
                ACCESS read-only
                STATUS mandatory
                DESCRIPTION
                    "The number of Key table entries for this device."
                ::= { tn3270DeviceEntry 5 }
            

            
            
            
            
            
            
            tn3270DeviceScreenNumber OBJECT-TYPE
                SYNTAX INTEGER
                ACCESS read-only
                STATUS mandatory
                DESCRIPTION
                    "The number of Screen table entries for this 
                    device."
                ::= { tn3270DeviceEntry 6 }






































            
            
            
            
            
            
            -- The Key table
            
            tn3270KeyTable OBJECT-TYPE
                SYNTAX SEQUENCE OF Tn3270KeyEntry
                ACCESS not-accessible
                STATUS mandatory
                DESCRIPTION
                    "A list of tn3270 key entries by device."
                ::= { tn3270 5 }
            
            tn3270KeyEntry OBJECT-TYPE
                SYNTAX Tn3270KeyEntry
                ACCESS not-accessible
                STATUS mandatory
                DESCRIPTION
                    "Tn3270 parameter values for a key entry for a 
                    device."
                INDEX { tn3270KeyDeviceName, tn3270KeyName }
                ::= { tn3270KeyTable 1 }
            
            Tn3270KeyEntry ::=
                SEQUENCE {
                    tn3270KeyDeviceName
                        DisplayString,
                    tn3270KeyName
                        DisplayString,
                    tn3270KeyStatus
                        INTEGER,
                    tn3270KeyCharacterSequence
                        OCTET STRING,
                    tn3270KeyDescription
                        DisplayString
                }
            
            tn3270KeyDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270KeyEntry 1 }
            
            tn3270KeyName OBJECT-TYPE

            
            
            
            
            
            
                SYNTAX INTEGER { newline(1), tab(2), backtab(3),
                                 cursorup(4), cursorleft(5),
                                 cursorright(6), cursordown(7),
                                 home(8), delete(9), eraseeof(10),
                                 eraseinput(11), insert(12),
                                 flushinput(13), refresh(14),
                                 centsign(15), duplicate(16),
                                 fieldmark(17), scroll(18),
                                 status(19), reset(20),
                                 fastleft(21), fastright(22),
                                 showkeys(23), print(24),
                                 pf1(39), pf2(40), pf3(41),
                                 pf4(42), pf5(43), pf6(44),
                                 pf7(45), pf8(46), pf9(47), pf10(48),
                                 pf11(49), pf12(50), pf13(51),
                                 pf14(52), pf15(53), pf16(54),
                                 pf17(55), pf18(56), pf19(57),
                                 pf20(58), pf21(59), pf22(60),
                                 pf23(61), pf24(62), pa1(63),
                                 pa2(64), pa3(65), sysreq(66),
                                 enter(67), clear(68), cursorsel(69),
                                 test(70) }
                ACCESS read-only
                STATUS mandatory
                DESCRIPTION
                    "The key name to which this entry applies.  
                    Corresponds directly to the key portion of SERVER 
                    TN3270 DEVICE KEYMAP and the value labeled 
                    '3270-key' in the 'Keymap:' section of the SERVER 
                    TN3270 DEVICE display."
                ::= { tn3270KeyEntry 2 }
            
            tn3270KeyStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270KeyEntry 3 }
            
            tn3270KeyCharacterSequence OBJECT-TYPE
                SYNTAX OCTET STRING (SIZE (0..8))

            
            
            
            
            
            
                ACCESS read-write
                STATUS mandatory
                DESCRIPTION
                    "The ASCII character sequence for the key.  
                    Corresponds directly to the escape-sequence portion 
                    of SERVER TN3270 DEVICE KEYMAP and the value labeled 
                    'KeyCode' in the 'Keymap:' section of the SERVER 
                    TN3270 DEVICE display."
                ::= { tn3270KeyEntry 4 }
            
            tn3270KeyDescription OBJECT-TYPE
                SYNTAX DisplayString (SIZE (0..5))
                ACCESS read-write
                STATUS mandatory
                DESCRIPTION
                    "Descriptive text for the key.  Corresponds directly 
                    to the description portion of SERVER TN3270 DEVICE 
                    KEYMAP and the value labeled 'Description' in the 
                    SERVER TN3270 DEVICE display."
                ::= { tn3270KeyEntry 5 }
            

























            
            
            
            
            
            
            -- The Screen Action table
            
            tn3270ScreenTable OBJECT-TYPE
                SYNTAX SEQUENCE OF Tn3270ScreenEntry
                ACCESS not-accessible
                STATUS mandatory
                DESCRIPTION
                    "A list of tn3270 screen action entries by device."
                ::= { tn3270 6 }
            
            tn3270ScreenEntry OBJECT-TYPE
                SYNTAX Tn3270ScreenEntry
                ACCESS not-accessible
                STATUS mandatory
                DESCRIPTION
                    "Tn3270 parameter values for a screen action entry 
                    for a device."
                INDEX { tn3270ScreenDeviceName, tn3270ScreenActionName }
                ::= { tn3270ScreenTable 1 }
            
            Tn3270ScreenEntry ::=
                SEQUENCE {
                    tn3270ScreenDeviceName
                        DisplayString,
                    tn3270ScreenActionName
                        INTEGER,
                    tn3270ScreenStatus
                        INTEGER,
                    tn3270ScreenCharacterSequence
                        OCTET STRING
                }
            
            tn3270ScreenDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270ScreenEntry 1 }
            
            tn3270ScreenActionName OBJECT-TYPE
                SYNTAX INTEGER { eraseeol(1), clearscr(2),
                                 movecursor(3), col132(4), col80(5),

            
            
            
            
            
            
                                 beep(6), charset(7), boldon(8),
                                 boldoff(9), blinkon(10),
                                 blinkoff(11), underscoreon(12),
                                 underscoreoff(13), reverseon(14),
                                 reverseoff(15),
                                 status1(26), status2(27),
                                 reset1(28), reset2(29),
                                 reset3(30), reset4(31),
                                 base(32), sgr(33) }
                ACCESS read-only
                STATUS mandatory
                DESCRIPTION
                    "The screen action to which this entry applies.  
                    Corresponds directly to the action portion of SERVER 
                    TN3270 DEVICE SCREENMAP and the value labeled 
                    'Terminal Function' in the 'Screenmap: section of 
                    the SERVER TN3270 DEVICE display."
                ::= { tn3270ScreenEntry 2 }
            
            tn3270ScreenStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270ScreenEntry 3 }
            
            tn3270ScreenCharacterSequence OBJECT-TYPE
                SYNTAX OCTET STRING (SIZE (0..15))
                ACCESS read-write
                STATUS mandatory
                DESCRIPTION
                    "The ASCII character sequence for the screen action.  
                    Some actions may have a lesser length limit.  
                    Corresponds directly to the escape-sequence portion 
                    of SERVER TN3270 DEVICE SCREENMAP and the value 
                    labeled 'HexCode' in the 'Screenmap: section of the 
                    SERVER TN3270 DEVICE display."
                ::= { tn3270ScreenEntry 4 }
            


            
            
            
            
            
            
            -- The Language table
            
            tn3270LanguageTable OBJECT-TYPE
                SYNTAX SEQUENCE OF Tn3270LanguageEntry
                ACCESS not-accessible
                STATUS mandatory
                DESCRIPTION
                    "A list of tn3270 language entries."
                ::= { tn3270 7 }
            
            tn3270LanguageEntry OBJECT-TYPE
                SYNTAX Tn3270LanguageEntry
                ACCESS not-accessible
                STATUS mandatory
                DESCRIPTION
                    "Tn3270 parameter values for a language entry."
                INDEX { tn3270LanguageName }
                ::= { tn3270LanguageTable 1 }
            
            Tn3270LanguageEntry ::=
                SEQUENCE {
                    tn3270LanguageName
                        DisplayString,
                    tn3270LanguageStatus
                        INTEGER
                }
            
            tn3270LanguageName OBJECT-TYPE
                SYNTAX DisplayString (SIZE (1..8))
                ACCESS read-write
                STATUS mandatory
                DESCRIPTION
                    "The name of language for character translation 
                    tables.  Corresponds directly to SERVER TN3270 
                    LANGUAGE and the value labeled 'Language Name:' in 
                    the SERVER LANGUAGE display."
                ::= { tn3270LanguageEntry 1 }
            
            tn3270LanguageStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 

            
            
            
            
            
            
                            agent removes an invalidated entry from the table."
                DEFVAL { valid }
                ::= { tn3270LanguageEntry 2 }
            










































            
            
            
            
            
            
            -- The Language EBCDIC to ASCII table
            
            eToALanguageTable OBJECT-TYPE
                SYNTAX SEQUENCE OF EToALanguageEntry
                ACCESS not-accessible
                STATUS mandatory
                DESCRIPTION
                    "A list of language EBCDIC to ASCII conversion 
                    entries."
                ::= { tn3270 8 }
            
            eToALanguageEntry OBJECT-TYPE
                SYNTAX EToALanguageEntry
                ACCESS not-accessible
                STATUS mandatory
                DESCRIPTION
                    "EBCDIC to ASCII parameter values for a language 
                    entry."
                INDEX { eToALanguageName, eToAOffset }
                ::= { eToALanguageTable 1 }
            
            EToALanguageEntry ::=
                SEQUENCE {
                    eToALanguageName
                        DisplayString,
                    eToAOffset
                        INTEGER,
                    eToAValue
                        INTEGER
                }
            
            eToALanguageName OBJECT-TYPE
                SYNTAX DisplayString (SIZE (1..8))
                ACCESS read-only
                STATUS mandatory
                DESCRIPTION
                    "The name of language from the language table."
                ::= { eToALanguageEntry 1 }
            
            eToAOffset OBJECT-TYPE
                SYNTAX INTEGER (65..256)
                ACCESS read-only
                STATUS mandatory
                DESCRIPTION
                    "EBCDIC character offset plus one, that is, the 
                    value 1 corresponds to an operational offset of 0.  

            
            
            
            
            
            
                            Corresponds directly to the offset portion of SERVER 
                    TN3270 LANGUAGE and the hexadecimal labels around 
                    the conversion table labeled 'EBCDIC to ASCII' in 
                    the SERVER LANGUAGE display."
                ::= { eToALanguageEntry 2 }
            
            eToAValue OBJECT-TYPE
                SYNTAX INTEGER (32..255)
                ACCESS read-write
                STATUS mandatory
                DESCRIPTION
                    "ASCII character value for the EBCDIC offset.  
                    Corresponds directly to the value portion of SERVER 
                    TN3270 LANGUAGE and the values in the conversion 
                    table labeled 'EBCDIC to ASCII' in the SERVER 
                    LANGUAGE display."
                ::= { eToALanguageEntry 3 }
            




























            
            
            
            
            
            
            -- The Language ASCII to EBCDIC table
            
            aToELanguageTable OBJECT-TYPE
                SYNTAX SEQUENCE OF AToELanguageEntry
                ACCESS not-accessible
                STATUS mandatory
                DESCRIPTION
                    "A list of language ASCII to EBCDIC conversion 
                    entries."
                ::= { tn3270 9 }
            
            aToELanguageEntry OBJECT-TYPE
                SYNTAX AToELanguageEntry
                ACCESS not-accessible
                STATUS mandatory
                DESCRIPTION
                    "ASCII to EBCDIC parameter values for a language 
                    entry."
                INDEX { aToELanguageName, aToEOffset }
                ::= { aToELanguageTable 1 }
            
            AToELanguageEntry ::=
                SEQUENCE {
                    aToELanguageName
                        DisplayString,
                    aToEOffset
                        INTEGER,
                    aToEValue
                        INTEGER
                }
            
            aToELanguageName OBJECT-TYPE
                SYNTAX DisplayString (SIZE (1..8))
                ACCESS read-only
                STATUS mandatory
                DESCRIPTION
                    "The name of language from the language table."
                ::= { aToELanguageEntry 1 }
            
            aToEOffset OBJECT-TYPE
                SYNTAX INTEGER (33..256)
                ACCESS read-only
                STATUS mandatory
                DESCRIPTION
                    "ASCII character offset plus one, that is, the value 
                    1 corresponds to an operational offset of 0.  

            
            
            
            
            
            
                            Corresponds directly to the offset portion of SERVER 
                    TN3270 LANGUAGE and the hexadecimal labels around 
                    the conversion table labeled 'ASCII to EBCDIC' in 
                    the SERVER LANGUAGE display."
                ::= { aToELanguageEntry 2 }
            
            aToEValue OBJECT-TYPE
                SYNTAX INTEGER (64..255)
                ACCESS read-write
                STATUS mandatory
                DESCRIPTION
                    "EBCDIC character value for the ASCII offset.  
                    Corresponds directly to the value portion of SERVER 
                    TN3270 LANGUAGE and the values in the conversion 
                    table labeled 'ASCII to EBCDIC' in the SERVER 
                    LANGUAGE display."
                ::= { aToELanguageEntry 3 }
            




























            
            
            
            
            
            
            -- the tn3270 Port table
            
            tn3270PortTable OBJECT-TYPE
                SYNTAX SEQUENCE OF Tn3270PortEntry
                ACCESS not-accessible
                STATUS mandatory
                DESCRIPTION
                    "A list of tn3270 character port entries."
                ::= { tn3270 10 }
            
            tn3270PortEntry OBJECT-TYPE
                SYNTAX Tn3270PortEntry
                ACCESS not-accessible
                STATUS mandatory
                DESCRIPTION
                    "Parameter values for a tn3270 port."
                INDEX { tn3270PortIndex }
                ::= { tn3270PortTable 1 }
            
            Tn3270PortEntry ::=
                SEQUENCE {
                    tn3270PortIndex
                        INTEGER,
                    tn3270PortDeviceName
                        DisplayString,
                    tn3270PortLanguageName
                        DisplayString,
                    tn3270PortExtendedAttributes
                        INTEGER,
                    tn3270PortEorNegotiation
                        INTEGER,
                    tn3270PortErrorLock
                        INTEGER
                }
            
            tn3270PortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { tn3270PortEntry 1 }
            

            
            
            
            
            
            
            tn3270PortDeviceName OBJECT-TYPE
                SYNTAX DisplayString (SIZE (1..8))
                ACCESS read-write
                STATUS mandatory
                DESCRIPTION
                    "The name of a generic terminal device from the 
                    tn3270 device table.  Corresponds directly to PORT 
                    TELNET TN3270 DEVICE and the value labeled 'Tn3270 
                    Device:' in the PORT TELNET display."
                ::= { tn3270PortEntry 2 }
            
            tn3270PortLanguageName OBJECT-TYPE
                SYNTAX DisplayString (SIZE (1..8))
                ACCESS read-write
                STATUS mandatory
                DESCRIPTION
                    "The name of language from the tn3270 language 
                    table.  Corresponds directly to PORT TELNET TN3270 
                    LANGUAGE and the value labeled 'Tn3270 Language:' in 
                    the PORT TELNET display."
                ::= { tn3270PortEntry 3 }
            
            tn3270PortExtendedAttributes OBJECT-TYPE
                SYNTAX INTEGER { disabled(1), enabled(2) }
                ACCESS read-write
                STATUS mandatory
                DESCRIPTION
                    "A control indicating that certain 3270 extended 
                    attributes are supported on the port.  Corresponds 
                    directly to PORT TELNET TN3270 XTDATTRS and the 
                    label 'Tn3270 XtdAttrs' following the label 'Enabled 
                    Characteristics' in the PORT TELNET display."
                ::= { tn3270PortEntry 4 }
            
            tn3270PortEorNegotiation OBJECT-TYPE
                SYNTAX INTEGER { disabled(1), enabled(2) }
                ACCESS read-write
                STATUS mandatory
                DESCRIPTION
                    "A control for negotiation of the Telnet EOR option 
                    when establishing a tn3270 session on the port.  
                    Corresponds directly to PORT TELNET TN3270 EOR and 
                    the label 'Tn3270 EOR' following the label 'Enabled 
                    Characteristics' in the PORT TELNET display."
                ::= { tn3270PortEntry 5 }
            

            
            
            
            
            
            
            tn3270PortErrorLock OBJECT-TYPE
                SYNTAX INTEGER { disabled(1), enabled(2) }
                ACCESS read-write
                STATUS mandatory
                DESCRIPTION
                    "A control for requiring use the RESET key when the 
                    host reports an error during a tn3270 session on the 
                    port.  Corresponds directly to PORT TELNET TN3270 
                    ERRORLOCK and the label 'Tn3270 ErrorLock' following 
                    the label 'Enabled Characteristics' in the PORT 
                    TELNET display."
                ::= { tn3270PortEntry 6 }


































            
            
            
            
            
            
            -- the Kerberos group
            
            -- Implementation of this group is mandatory for all Xyplex
            -- systems that implement a Kerberos client
            
            kerbStatus OBJECT-TYPE
                SYNTAX INTEGER { none(1), login(2) }
                ACCESS read-write
                STATUS mandatory
                DESCRIPTION
                    "A control indicating the level of Kerberos 
                    operation on the system.  Corresponds directly to 
                    SERVER KERBEROS STATUS and the value labeled 
                    'Kerberos Security:' in the SERVER KERBEROS 
                    display."
                ::= { kerberos 1 }
            
            kerbRealm OBJECT-TYPE
                SYNTAX DisplayString (SIZE (0..40))
                ACCESS read-write
                STATUS mandatory
                DESCRIPTION
                    "The Kerberos realm with which the kerbServerName1 
                    and kerbServerName2 are associated.  Corresponds 
                    directly to SERVER KERBEROS REALM and the value 
                    labeled 'Kerberos Realm:' in the SERVER KERBEROS 
                    display."
                ::= { kerberos 2 }
            
            kerbQueryLimit OBJECT-TYPE
                SYNTAX INTEGER (1..16)
                ACCESS read-write
                STATUS mandatory
                DESCRIPTION
                    "The maximum number of attempts the system can make 
                    when trying to verify a Kerberos ID.  Corresponds 
                    directly to SERVER KERBEROS QUERY LIMIT and the 
                    value labeled 'Kerberos Query Limit:' in the SERVER 
                    KERBEROS display."
                ::= { kerberos 3 }
            
            kerbMasterName OBJECT-TYPE
                SYNTAX DisplayString (SIZE (0..50))
                ACCESS read-write
                STATUS mandatory
                DESCRIPTION

            
            
            
            
            
            
                    "The Domain name of the Kerberos master host system, 
                    which holds the Kerberos database.  Corresponds 
                    directly to SERVER KERBEROS MASTER and the value 
                    labeled 'Kerberos Master:' in the SERVER KERBEROS 
                    display."
                ::= { kerberos 4 }
            
            kerbServerName1 OBJECT-TYPE
                SYNTAX DisplayString (SIZE (0..50))
                ACCESS read-write
                STATUS mandatory
                DESCRIPTION
                    "The Domain name of the first Kerberos server to try 
                    when the system verifys a Kerberos ID.  Corresponds 
                    directly to SERVER KERBEROS PRIMARY SERVER and the 
                    value labeled 'Kerberos Primary Server:' in the 
                    SERVER KERBEROS display."
                ::= { kerberos 5 }
            
            kerbServerName2 OBJECT-TYPE
                SYNTAX DisplayString (SIZE (0..50))
                ACCESS read-write
                STATUS mandatory
                DESCRIPTION
                    "The Domain name of the Kerberos server to try when 
                    the system verifys a Kerberos ID and cannot reach 
                    the Kerberos primary server.  Corresponds directly 
                    to SERVER KERBEROS SECONDARY SERVER and the value 
                    labeled 'Kerberos Secondary Server:' in the SERVER 
                    KERBEROS display."
                ::= { kerberos 6 }
            
            kerbInsecureLogins OBJECT-TYPE
                SYNTAX Counter
                ACCESS read-only
                STATUS mandatory
                DESCRIPTION
                    "The number of user logins on ports for which 
                    Kerberos user verification is not enabled.  
                    Corresponds directly to the value labeled 'Logins 
                    without Kerberos:' in the SERVER KERBEROS display."
                ::= { kerberos 7 }
            
            kerbSecureLogins OBJECT-TYPE
                SYNTAX Counter
                ACCESS read-only

            
            
            
            
            
            
                STATUS mandatory
                DESCRIPTION
                    "The number of successful user logins on ports for 
                    which Kerberos user verification is enabled.  
                    Corresponds directly to the value labeled 
                    'Successful Logins:' in the SERVER KERBEROS 
                    display."
                ::= { kerberos 8 }
            
            kerbSecureLoginsFailed OBJECT-TYPE
                SYNTAX Counter
                ACCESS read-only
                STATUS mandatory
                DESCRIPTION
                    "The number of verification failures due to 
                    incorrect ID or password for attempted user logins 
                    on ports for which Kerberos user verification is 
                    enabled.  Corresponds directly to the value labeled 
                    'Unsuccessful Logins:' in the SERVER KERBEROS 
                    display."
                ::= { kerberos 9 }
            
            kerbPasswordChangeFailed OBJECT-TYPE
                SYNTAX Counter
                ACCESS read-only
                STATUS mandatory
                DESCRIPTION
                    "The number of user failures to change their 
                    Kerberos password due to invalid old password or new 
                    password verification.  Corresponds directly to the 
                    value labeled 'Password Change Failures:' in the 
                    SERVER KERBEROS display."
                ::= { kerberos 10 }
            
            kerbError OBJECT-TYPE
                SYNTAX INTEGER
                ACCESS read-only
                STATUS mandatory
                DESCRIPTION
                    "The error number of the most recent 
                    Kerberos-related failure.  Corresponds directly to 
                    the value labeled 'Last Kerberos Error:' in the 
                    SERVER KERBEROS display.  For a list of error 
                    numbers and their meanings, consult relevant Xyplex 
                    or Kerberos documentation."
                ::= { kerberos 11 }

            
            
            
            
            
            
            
            kerbErrorTime OBJECT-TYPE
                SYNTAX DateTime
                ACCESS read-only
                STATUS mandatory
                DESCRIPTION
                    "The date and time that kerbError was last updated.  
                    Corresponds directly to the value labeled 
                    'Occurred:' in the SERVER KERBEROS display."
                ::= { kerberos 12 }
            
            kerbMasterAccess OBJECT-TYPE
                SYNTAX Counter
                ACCESS read-only
                STATUS mandatory
                DESCRIPTION
                    "The number of times the system successfully 
                    accessed the Kerberos master host.  Corresponds 
                    directly to the value labeled 'Attempts to access:', 
                    'Master', and 'Successful:' in the SERVER KERBEROS 
                    display."
                ::= { kerberos 13 }
            
            kerbMasterAccessFailed OBJECT-TYPE
                SYNTAX Counter
                ACCESS read-only
                STATUS mandatory
                DESCRIPTION
                    "The number of times the system failed access to the 
                    Kerberos master host.  Corresponds directly to the 
                    value labeled 'Attempts to access:', 'Master', and 
                    'Unsuccessful:' in the SERVER KERBEROS display."
                ::= { kerberos 14 }
            
            kerbServerAccess1 OBJECT-TYPE
                SYNTAX Counter
                ACCESS read-only
                STATUS mandatory
                DESCRIPTION
                    "The number of times the system successfully 
                    accessed the Kerberos primary server.  Corresponds 
                    directly to the value labeled 'Attempts to access:', 
                    'Server1', and 'Successful:' in the SERVER KERBEROS 
                    display."
                ::= { kerberos 15 }
            

            
            
            
            
            
            
            kerbServerAccessFailed1 OBJECT-TYPE
                SYNTAX Counter
                ACCESS read-only
                STATUS mandatory
                DESCRIPTION
                    "The number of times the system failed access to the 
                    Kerberos primary server.  Corresponds directly to 
                    the value labeled 'Attempts to access:', 'Server1', 
                    and 'Unsuccessful:' in the SERVER KERBEROS 
                    display."
                ::= { kerberos 16 }
            
            kerbServerAccess2 OBJECT-TYPE
                SYNTAX Counter
                ACCESS read-only
                STATUS mandatory
                DESCRIPTION
                    "The number of times the system successfully 
                    accessed the Kerberos secondary server.  Corresponds 
                    directly to the value labeled 'Attempts to access:', 
                    'Server2', and 'Successful:' in the SERVER KERBEROS 
                    display."
                ::= { kerberos 17 }
            
            kerbServerAccessFailed2 OBJECT-TYPE
                SYNTAX Counter
                ACCESS read-only
                STATUS mandatory
                DESCRIPTION
                    "The number of times the system failed access to the 
                    Kerberos secondary server.  Corresponds directly to 
                    the value labeled 'Attempts to access:', 'Server2', 
                    and 'Unsuccessful:' in the SERVER KERBEROS 
                    display."
                ::= { kerberos 18 }











            
            
            
            
            
            
            -- the Kerberos Port table
            
            kerbPortTable OBJECT-TYPE
                SYNTAX SEQUENCE OF KerbPortEntry
                ACCESS not-accessible
                STATUS mandatory
                DESCRIPTION
                    "A list of Kerberos character port entries."
                ::= { kerberos 19 }
            
            kerbPortEntry OBJECT-TYPE
                SYNTAX KerbPortEntry
                ACCESS not-accessible
                STATUS mandatory
                DESCRIPTION
                    "Parameter values for a Kerberos port."
                INDEX { kerbPortIndex }
                ::= { kerbPortTable 1 }
            
            KerbPortEntry ::=
                SEQUENCE {
                    kerbPortIndex
                        INTEGER,
                    kerbPortStatus
                        INTEGER
                }
            
            kerbPortIndex OBJECT-TYPE
                SYNTAX INTEGER
                ACCESS read-only
                STATUS mandatory
                DESCRIPTION
                    "An index value that uniquely identifies a port 
                    could relate to Kerberos.  The port identified by a 
                    particular value of this index is the same port as 
                    identified by charPortIndex in the Character 
                    MIB [11]."
                ::= { kerbPortEntry 1 }
            
            kerbPortStatus OBJECT-TYPE
                SYNTAX INTEGER { none(1), login(2) }
                ACCESS read-write
                STATUS mandatory
                DESCRIPTION
                    "A control indicating the level of Kerberos 
                    operation on the port.  Corresponds directly to PORT 

            
            
            
            
            
            
                            KERBEROS and the value 'Kerberos' following the 
                    label 'Enabled Characteristics' in the PORT 
                    CHARACTERISTICS display."
                ::= { kerbPortEntry 2 }










































            
            
            
            
            
            
            -- the Port Security group
            
            -- Implementation of this group is mandatory for all Xyplex
            -- systems that implement Internet port security
            
            psEntryNumber OBJECT-TYPE
                SYNTAX INTEGER
                ACCESS read-only
                STATUS mandatory
                DESCRIPTION
                    "The number of security entries in this system's 
                    port security table with psEntryStatus of 'valid'."
                ::= { portSecurity 1 }
            
            psEntryNumberLimit OBJECT-TYPE
                SYNTAX INTEGER
                ACCESS read-only
                STATUS mandatory
                DESCRIPTION
                    "The maximum number of security entries in this 
                    system's port security table."
                ::= { portSecurity 2 }
            
            psEntryInvalidIndex OBJECT-TYPE
                SYNTAX INTEGER
                ACCESS read-only
                STATUS mandatory
                DESCRIPTION
                    "A value of psEntryIndex for an entry that has 
                    psEntryStatus of 'invalid'.  A management station 
                    may choose this value when adding a new entry.  
                    Collisions between independent management stations 
                    simultaneously using the same number are beyond the 
                    scope of this document."
                ::= { portSecurity 3 }











            
            
            
            
            
            
            -- the Port Security table
            
            psPortTable OBJECT-TYPE
                SYNTAX SEQUENCE OF PsPortEntry
                ACCESS not-accessible
                STATUS mandatory
                DESCRIPTION
                    "A list of port security character port entries."
                ::= { portSecurity 4 }
            
            psPortEntry OBJECT-TYPE
                SYNTAX PsPortEntry
                ACCESS not-accessible
                STATUS mandatory
                DESCRIPTION
                    "Port security parameter values for a port."
                INDEX { psPortIndex }
                ::= { psPortTable 1 }
            
            PsPortEntry ::=
                SEQUENCE {
                    psPortIndex
                        INTEGER,
                    psPortDefaultInboundAccess
                        INTEGER,
                    psPortDefaultOutboundAccess
                        INTEGER
                }
            
            psPortIndex OBJECT-TYPE
                SYNTAX INTEGER
                ACCESS read-only
                STATUS mandatory
                DESCRIPTION
                    "An index value that uniquely identifies a port for 
                    security purposes.  The port identified by a 
                    particular value of this index is the same port as 
                    identified by charPortIndex in the Proposed Standard 
                    Internet Character MIB."
                ::= { psPortEntry 1 }
            
            psPortDefaultInboundAccess OBJECT-TYPE
                SYNTAX INTEGER { allow(1), deny(2) }
                ACCESS read-write
                STATUS mandatory
                DESCRIPTION

            
            
            
            
            
            
                    "The default access to the port for incoming TCP 
                    connections.  Corresponds directly to PORT INTERNET 
                    SECURITY DEFAULT INBOUND and the value labeled 
                    'Inbound Default:' in the PORT INTERNET SECURITY 
                    display."
                ::= { psPortEntry 2 }
            
            psPortDefaultOutboundAccess OBJECT-TYPE
                SYNTAX INTEGER { allow(1), deny(2) }
                ACCESS read-write
                STATUS mandatory
                DESCRIPTION
                    "The default access to the port for outgoing TCP 
                    connections.  Corresponds directly to PORT INTERNET 
                    SECURITY DEFAULT OUTBOUND and the value labeled 
                    'Outbound Default:' in the PORT INTERNET SECURITY 
                    display."
                ::= { psPortEntry 3 }




























            
            
            
            
            
            
            -- the Port Security table
            
            psTable OBJECT-TYPE
                SYNTAX SEQUENCE OF PsEntry
                ACCESS not-accessible
                STATUS mandatory
                DESCRIPTION
                    "A list of port security entries."
                ::= { portSecurity 5 }
            
            psEntry OBJECT-TYPE
                SYNTAX PsEntry
                ACCESS not-accessible
                STATUS mandatory
                DESCRIPTION
                    "Port security parameter values for an entry for a 
                    port."
                INDEX { psEntryIndex }
                ::= { psTable 1 }
            
            PsEntry ::=
                SEQUENCE {
                    psEntryIndex
                        INTEGER,
                    psEntryStatus
                        INTEGER,
                    psEntryAddress
                        IpAddress,
                    psEntryMask
                        IpAddress,
                    psEntryAccess
                        INTEGER,
                    psEntryDirection
                        INTEGER,
                    psEntryPortMap
                        OCTET STRING
                }
            
            psEntryIndex OBJECT-TYPE
                SYNTAX INTEGER
                ACCESS read-only
                STATUS mandatory
                DESCRIPTION
                    "A small, numeric distinguisher for port security 
                    entries.  When adding a new entry, the client should 
                    specify an unused value, such as 

            
            
            
            
            
            
                            psEntryInvalidIndex.  Corresponds directly to the 
                    value labeled 'Entry' in the SERVER INTERNET 
                    SECURITY display."
                ::= { psEntry 1 }
            
            psEntryStatus OBJECT-TYPE
                SYNTAX INTEGER { invalid(1), valid(2) }
                ACCESS read-write
                STATUS mandatory
                DESCRIPTION
                    "Status of this entry.  Setting the value to 
                    'invalid' invalidates the entry, corresponding 
                    directly to the CLEAR INTERNET SECURITY command.  It 
                    is an implementation-specific matter as to whether 
                    the agent removes an invalidated entry from the 
                    table.  When creating a new instance, 
                    psEntryAddress, psEntryMask, psEntryAccess, and 
                    psEntryDirection for the new instance must be 
                    present in the set request."
                DEFVAL { valid }
                ::= { psEntry 2 }
            
            psEntryAddress OBJECT-TYPE
                SYNTAX IpAddress
                ACCESS read-write
                STATUS mandatory
                DESCRIPTION
                    "The IP address to which the entry pertains.  
                    Corresponds directly to the PORT INTERNET SECURITY 
                    internet address and the value labeled 'Internet 
                    Address' in the SERVER INTERNET SECURITY display."
                ::= { psEntry 3 }
            
            psEntryMask OBJECT-TYPE
                SYNTAX IpAddress
                ACCESS read-write
                STATUS mandatory
                DESCRIPTION
                    "The mask applied to psEntryAddress when making a 
                    security check based on this entry.  Corresponds 
                    directly to PORT INTERNET SECURITY MASK and the 
                    value labeled 'Security Mask' in the SERVER INTERNET 
                    SECURITY display."
                ::= { psEntry 4 }
            
            psEntryAccess OBJECT-TYPE

            
            
            
            
            
            
                SYNTAX INTEGER { allow(1), deny(2) }
                ACCESS read-write
                STATUS mandatory
                DESCRIPTION
                    "The access to the port for TCP connections when 
                    making a security check based on this entry.  
                    Corresponds directly to PORT INTERNET SECURITY ALLOW 
                    or DENY and the value labeled 'Access' in the SERVER 
                    INTERNET SECURITY display."
                ::= { psEntry 5 }
            
            psEntryDirection OBJECT-TYPE
                SYNTAX INTEGER { inbound(1), outbound(2) }
                ACCESS read-write
                STATUS mandatory
                DESCRIPTION
                    "The direction of TCP connections to which this 
                    entry applies.  Corresponds directly to PORT 
                    INTERNET SECURITY INBOUND or OUTBOUND and the value 
                    labeled 'Direction' in the SERVER INTERNET SECURITY 
                    display."
                ::= { psEntry 6 }
            
            psEntryPortMap OBJECT-TYPE
                SYNTAX OCTET STRING
                ACCESS read-write
                STATUS mandatory
                DESCRIPTION
                    "The list of character ports to which this entry 
                    applies.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to PORT INTERNET SECURITY and 
                    the value labeled 'Ports' in the SERVER INTERNET 
                    SECURITY display."
                ::= { psEntry 7 }







            
            
            
            
            
            
            -- the XREMOTE group
            
            -- Implementation of this group is mandatory for all Xyplex
            -- systems that implement XREMOTE
            
            xremoteServerName1 OBJECT-TYPE
                SYNTAX DisplayString (SIZE (0..50))
                ACCESS read-write
                STATUS mandatory
                DESCRIPTION
                    "The Domain name of the first XREMOTE font server to 
                    try for downloading fonts.  Corresponds directly to 
                    SERVER XREMOTE PRIMARY SERVER and the value labeled 
                    'Xremote Primary Font Server:' in the SERVER XREMOTE 
                    display."
                ::= { xremote 1 }
            
            xremoteServerName2 OBJECT-TYPE
                SYNTAX DisplayString (SIZE (0..50))
                ACCESS read-write
                STATUS mandatory
                DESCRIPTION
                    "The Domain name of the XREMOTE font server to try 
                    for downloading fonts and the primary font server 
                    does not respond.  Corresponds directly to SERVER 
                    XREMOTE SECONDARY SERVER and the value labeled 
                    'Xremote Secondary Font Server:' in the SERVER 
                    XREMOTE display."
                ::= { xremote 2 }
            
            xremoteServerAccess1 OBJECT-TYPE
                SYNTAX Counter
                ACCESS read-only
                STATUS mandatory
                DESCRIPTION
                    "The number of times the system successfully 
                    accessed the XREMOTE primary font server.  
                    Corresponds directly to the value labeled 'Attempts 
                    to access:', 'Server1', and 'Successful:' in the 
                    SERVER XREMOTE display."
                ::= { xremote 3 }
            
            xremoteServerAccessFailed1 OBJECT-TYPE
                SYNTAX Counter
                ACCESS read-only
                STATUS mandatory

            
            
            
            
            
            
                DESCRIPTION
                    "The number of times the system failed access to the 
                    XREMOTE primary font server.  Corresponds directly 
                    to the value labeled 'Attempts to access:', 
                    'Server1', and 'Unsuccessful:' in the SERVER XREMOTE 
                    display."
                ::= { xremote 4 }
            
            xremoteServerAccess2 OBJECT-TYPE
                SYNTAX Counter
                ACCESS read-only
                STATUS mandatory
                DESCRIPTION
                    "The number of times the system successfully 
                    accessed the XREMOTE secondary font server.  
                    Corresponds directly to the value labeled 'Attempts 
                    to access:', 'Server2', and 'Successful:' in the 
                    SERVER XREMOTE display."
                ::= { xremote 5 }
            
            xremoteServerAccessFailed2 OBJECT-TYPE
                SYNTAX Counter
                ACCESS read-only
                STATUS mandatory
                DESCRIPTION
                    "The number of times the system failed access to the 
                    XREMOTE secondary font server.  Corresponds directly 
                    to the value labeled 'Attempts to access:', 
                    'Server2', and 'Unsuccessful:' in the SERVER XREMOTE 
                    display."
                ::= { xremote 6 }
            
            xremoteSessions OBJECT-TYPE
                SYNTAX Gauge
                ACCESS read-only
                STATUS mandatory
                DESCRIPTION
                    "The number of connected XREMOTE sessions.  
                    Corresponds directly to the value labeled 'Current 
                    Number of Xremote Sessions:' in the SERVER XREMOTE 
                    display."
                ::= { xremote 7 }
            
            -- Additional individual objects follow port table


            
            
            
            
            
            
            -- the XREMOTE Port table
            
            xremotePortTable OBJECT-TYPE
                SYNTAX SEQUENCE OF XremotePortEntry
                ACCESS not-accessible
                STATUS mandatory
                DESCRIPTION
                    "A list of XREMOTE character port entries."
                ::= { xremote 8 }
            
            xremotePortEntry OBJECT-TYPE
                SYNTAX XremotePortEntry
                ACCESS not-accessible
                STATUS mandatory
                DESCRIPTION
                    "XREMOTE parameter values for a port."
                INDEX { psPortIndex }
                ::= { xremotePortTable 1 }
            
            XremotePortEntry ::=
                SEQUENCE {
                    xremotePortIndex
                        INTEGER,
                    xremotePortXremote
                        INTEGER,
                    xremotePortXdmQuery
                        INTEGER,
                    xremotePortXdmHost
                        DisplayString
                }
            
            xremotePortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { xremotePortEntry 1 }
            
            xremotePortXremote OBJECT-TYPE
                SYNTAX INTEGER { disabled(1), enabled(2) }
                ACCESS read-write

            
            
            
            
            
            
                STATUS mandatory
                DESCRIPTION
                    "Control for use of XREMOTE on the port.  
                    Corresponds directly to PORT XREMOTE and the 
                    presence of the label 'Xremote' following the label 
                    'Enabled Characteristics:' in the PORT 
                    CHARACTERISTICS display."
                ::= { xremotePortEntry 2 }
            
            xremotePortXdmQuery OBJECT-TYPE
                SYNTAX INTEGER { specific(1), broadcast(2),
                                 indirect(3) }
                ACCESS read-write
                STATUS mandatory
                DESCRIPTION
                    "The type of query message issued by a port when 
                    searching for an X Display Manager (XDM). 
                    Corresponds directly to the PORT XDM QUERY and the 
                    'XDM Query:' in the PORT ALTERNATE CHARACTERISTICS 
                    display"
                ::= { xremotePortEntry 3 }
            
            xremotePortXdmHost OBJECT-TYPE
                SYNTAX DisplayString (SIZE (0..50))
                ACCESS read-write
                STATUS mandatory
                DESCRIPTION
                    "The Domain name or Internet address of the X 
                    Display Manager (XDM) for a port. Corresponds 
                    directly to the PORT XDM HOST and the 'XDM Host:' in 
                    the PORT ALTERNATE CHARACTERISTICS display"
                ::= { xremotePortEntry 4 }
            
            -- Additional individual objects
            
            xremoteServerClients OBJECT-TYPE
                SYNTAX Gauge
                ACCESS read-only
                STATUS mandatory
                DESCRIPTION
                    "The number of active X clients.  Corresponds 
                    directly to the value labeled 'Current Number of 
                    XClients:' in the SERVER XREMOTE display."
                ::= { xremote 9 }


            
            
            
            
            
            
            -- the Rotary group
            
            -- Implementation of this group is mandatory for all Xyplex
            -- systems that implement rotaries
            
            rotaryNumber OBJECT-TYPE
                SYNTAX INTEGER
                ACCESS read-only
                STATUS mandatory
                DESCRIPTION
                    "The number of entries in the Rotary  table."
                ::= { rotary 1 }


































            
            
            
            
            
            
            -- The Rotary  table
            
            rotaryTable OBJECT-TYPE
                SYNTAX SEQUENCE OF RotaryEntry
                ACCESS not-accessible
                STATUS mandatory
                DESCRIPTION
                    "A list of rotary  entries."
                ::= { rotary 2 }
            
            rotaryEntry OBJECT-TYPE
                SYNTAX RotaryEntry
                ACCESS not-accessible
                STATUS mandatory
                DESCRIPTION
                    "Parameter values for a rotary."
                INDEX { rotaryAddress }
                ::= { rotaryTable 1 }
            
            RotaryEntry ::=
                SEQUENCE {
                    rotaryAddress
                        IpAddress,
                    rotaryStatus
                        INTEGER,
                    rotaryPortMap
                        OCTET STRING
                }
            
            rotaryAddress OBJECT-TYPE
                SYNTAX IpAddress
                ACCESS read-write
                STATUS mandatory
                DESCRIPTION
                    "The internet address to be recognized as a rotary.  
                    Corresponds directly to the ip-address portion of 
                    SERVER INTERNET ROTARY and the value labeled 
                    'Internet Address' in the SERVER INTERNET ROTARY 
                    display."
                ::= { rotaryEntry 1 }
            
            rotaryStatus OBJECT-TYPE
                SYNTAX INTEGER { invalid(1), valid(2) }
                ACCESS read-write
                STATUS mandatory
                DESCRIPTION

            
            
            
            
            
            
                    "Status of this entry.  Setting the value to 
                    'invalid' invalidates the entry, corresponding 
                    directly to the CLEAR SERVER INTERNET ROTARY 
                    command.  It is an implementation-specific matter as 
                    to whether the agent removes an invalidated entry 
                    from the table."
                DEFVAL { valid }
                ::= { rotaryEntry 2 }
            
            rotaryPortMap OBJECT-TYPE
                SYNTAX OCTET STRING
                ACCESS read-write
                STATUS mandatory
                DESCRIPTION
                    "The list of character ports that compose the 
                    rotary.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to port-list portion of SERVER 
                    INTERNET ROTARY and the value labeled 'Ports' in the 
                    SERVER INTERNET ROTARY display."
                ::= { rotaryEntry 3 }
            




















            
            
            
            
            
            
            -- the EGP group
            
            -- Implementation of this group is mandatory for all Xyplex
            -- systems that implement EGP
            
            egpRouting OBJECT-TYPE
                SYNTAX INTEGER { disabled(1), enabled(2) }
                ACCESS read-write
                STATUS mandatory
                DESCRIPTION
                    "Control for EGP routing services."
                ::= { xEgp 1 }
            
            egpStatus OBJECT-TYPE
                SYNTAX INTEGER { active(1), noMemory(2), noIpRouting(3),
                                 noEgpRouting(4), noNeighbors(5),
                                 noAS(6) }
                ACCESS read-only
                STATUS mandatory
                DESCRIPTION
                    "Status of the EGP routing services indicating why 
                    it is not running."
                ::= { xEgp 2 }
            
            egpNbrTable OBJECT-TYPE
                SYNTAX SEQUENCE OF EgpNbrEntry
                ACCESS not-accessible
                STATUS mandatory
                DESCRIPTION
                    "The EGP neighbor table."
                ::= { xEgp 3 }
            
            egpNbrEntry OBJECT-TYPE
                SYNTAX EgpNbrEntry
                ACCESS not-accessible
                STATUS mandatory
                DESCRIPTION
                    "Information about this entity's relationship with a 
                    particular EGP neighbor."
                INDEX { egpNbrAddr }
                ::= { egpNbrTable 1 }
            
            EgpNbrEntry ::=
                SEQUENCE {
                    egpNbrAddr
                        IpAddress,

            
            
            
            
            
            
                    egpNbrIntervalDead
                        INTEGER
                }
            
            egpNbrAddr OBJECT-TYPE
                SYNTAX IpAddress
                ACCESS read-only
                STATUS mandatory
                DESCRIPTION
                    "The IP address of this entry's EGP neighbor."
                ::= { egpNbrEntry 1 }
            
            egpNbrIntervalDead OBJECT-TYPE
                SYNTAX INTEGER
                ACCESS read-write
                STATUS mandatory
                DESCRIPTION
                    "The interval upon entering the cease or idle state 
                    before automatically assuming a Start Event has 
                    occured.  If a neighbor does not respond within 5 
                    minutes, a Stop Event will automatically occur.  The 
                    interval is in hundredths of seconds."
                DEFVAL { 30000 }
                ::= { egpNbrEntry 2 }
            





















            
            
            
            
            
            
            -- the OSPF group
            
            -- Implementation of this group is mandatory for all Xyplex
            -- systems that implement OSPF
            
            ospfAutoConfigure OBJECT-TYPE
                SYNTAX INTEGER { disabled(1), enabled(2) }
                ACCESS read-write
                STATUS mandatory
                DESCRIPTION
                    "Control whether OSPF will automatically configure 
                    itself."
                ::= { xospf 1 }
            
            ospfStatus OBJECT-TYPE
                SYNTAX INTEGER { active(1), noMemory(2), noIpRouting(3),
                                 noOspfRouting(4), noAreas(5),
                                 noInterfaces(6), noRtrId(7), 
                                 noBackBoneAndVirtualInterfaces(8),
                                 noBackBoneAndInterface(9),
                                 noBackBone(10) }
                ACCESS read-only
                STATUS mandatory
                DESCRIPTION
                    "Status of the OSPF routing services indicating why 
                    it is not running."
                ::= { xospf 2 }
            
            ospfIfMtrcTbl OBJECT-TYPE
                SYNTAX SEQUENCE OF OspfIfMtrcEntry
                ACCESS not-accessible
                STATUS mandatory
                DESCRIPTION
                    "The TOS metrics for a non-virtual interface 
                    identified by the interface index."
                ::= { xospf 3 }
            
            ospfIfMtrcEntry OBJECT-TYPE
                SYNTAX OspfIfMtrcEntry
                ACCESS not-accessible
                STATUS mandatory
                DESCRIPTION
                    "A particular TOS metric for a non-virtual interface 
                    identified by the interface index."
                INDEX { ospfIfMtrcIpAddress, ospfIfMtrcAddressLessIf,
                        ospfIfMtrcTos }

            
            
            
            
            
            
                ::= { ospfIfMtrcTbl 1 }
            
            OspfIfMtrcEntry ::=
                SEQUENCE {
                    ospfIfMtrcIpAddress
                        IpAddress,
                    ospfIfMtrcAddressLessIf
                        INTEGER,
                    ospfIfMtrcTos
                        INTEGER,
                    ospfIfMtrcCostActual
                        INTEGER
                }
            
            ospfIfMtrcIpAddress OBJECT-TYPE
                SYNTAX IpAddress
                ACCESS read-only
                STATUS mandatory
                DESCRIPTION
                    "Same as ospfIfMetricIpAddress in OSPF MIB, the IP 
                    address of this OSPF interface."
                REFERENCE
                    "OSPF Version 2 Management Information Base, RFC 
                    1253"
                ::= { ospfIfMtrcEntry 1 }
            
            ospfIfMtrcAddressLessIf OBJECT-TYPE
                SYNTAX INTEGER
                ACCESS read-only
                STATUS mandatory
                DESCRIPTION
                    "Same as ospfIfMetricAddressLessIf in OSPF MIB, for 
                    the purpose of easing the instancing of addressed 
                    and addressless interfaces.  This variable takes the 
                    value 0 on interfaces with IP Addresses, and the 
                    value of ifIndex for interfaces having no IP 
                    Address."
                REFERENCE
                    "OSPF Version 2 Management Information Base, RFC 
                    1253"
                ::= { ospfIfMtrcEntry 2 }
            
            ospfIfMtrcTos OBJECT-TYPE
                SYNTAX INTEGER ( 1..16 )
                ACCESS read-only
                STATUS mandatory

            
            
            
            
            
            
                DESCRIPTION
                    "Same as ospfIfMetricIpAddress in OSPF MIB, the type 
                    of service metric being referenced."
                REFERENCE
                    "OSPF Version 2 Management Information Base, RFC 
                    1253"
                ::= { ospfIfMtrcEntry 3 }
            
            ospfIfMtrcCostActual OBJECT-TYPE
                SYNTAX INTEGER ( 1..65535 )
                ACCESS read-only
                STATUS mandatory
                DESCRIPTION
                    "The actual cost of the metric in case it was set to 
                    auto."
                ::= { ospfIfMtrcEntry 4 }
            





























            
            
            
            
            
            
            -- the Router IP group
            
            -- Implementation of this group is mandatory for all Xyplex
            -- systems that implement IP and do through routing
            
            ipAddrExtensions OBJECT-TYPE
                SYNTAX SEQUENCE OF IpAdEntExt
                ACCESS not-accessible
                STATUS mandatory
                DESCRIPTION
                    "Table of additional fields indexed by local IP 
                    address.  An entry in this table is created or 
                    deleted when an entry in the ipAddrTable is created 
                    or deleted."
                ::= { routerIp 1 }
            
            ipAdEntExt OBJECT-TYPE
                SYNTAX IpAdEntExt
                ACCESS not-accessible
                STATUS mandatory
                DESCRIPTION
                    "A particular entry."
                INDEX { ipAdEntExtAddress }
                ::= { ipAddrExtensions 1 }
            
            IpAdEntExt ::=
                SEQUENCE {
                    ipAdEntExtAddress
                        IpAddress,
                    ipAdEntExtProxyArp
                        INTEGER,
                    ipAdEntExtRip
                        INTEGER
                }
            
            ipAdEntExtAddress OBJECT-TYPE
                SYNTAX IpAddress
                ACCESS read-only
                STATUS mandatory
                DESCRIPTION
                    "Same as ipAdEntAddr, a local address representing a 
                    network connection."
                ::= { ipAdEntExt 1 }
            
            ipAdEntExtProxyArp OBJECT-TYPE
                SYNTAX INTEGER { enabled(2), disabled(1) }   

            
            
            
            
            
            
                ACCESS read-write
                STATUS mandatory
                DESCRIPTION
                    "Controls whether proxy ARP is active for this local 
                    address."
                DEFVAL { disabled }
                ::= { ipAdEntExt 2 }
            
            ipAdEntExtRip OBJECT-TYPE
                SYNTAX INTEGER { enabled(2), disabled(1) }   
                ACCESS read-write
                STATUS mandatory
                DESCRIPTION
                    "Controls whether RIP as a router discovery protocol 
                    is active for this local address."
                DEFVAL { disabled }
                ::= { ipAdEntExt 3 }





























            
            
            
            
            
            
            -- the Router UDP group
            
            -- Implementation of this group is mandatory for all Xyplex
            -- systems that implement UDP and do through routing
            
            udpBcstServerTbl OBJECT-TYPE
                SYNTAX SEQUENCE OF UdpBcstServerEntry
                ACCESS not-accessible
                STATUS mandatory
                DESCRIPTION
                    "Table of servers to whom UDP broadcast messages 
                    will be forwarded."
                ::= { routerUdp 1 }
            
            udpBcstServerEntry OBJECT-TYPE
                SYNTAX UdpBcstServerEntry
                ACCESS not-accessible
                STATUS mandatory
                DESCRIPTION
                    "A particular entry."
                INDEX { udpBcstServerAddress }
                ::= { udpBcstServerTbl 1 }
            
            UdpBcstServerEntry ::=
                SEQUENCE {
                    udpBcstServerAddress
                        IpAddress,
                    udpBcstServerStatus
                        INTEGER
                }
            
            udpBcstServerAddress OBJECT-TYPE
                SYNTAX IpAddress
                ACCESS read-write
                STATUS mandatory
                DESCRIPTION
                    "Internet address of the server."
                ::= { udpBcstServerEntry 1 }
            
            udpBcstServerStatus OBJECT-TYPE
                SYNTAX INTEGER { invalid(1), valid(2) }
                ACCESS read-write
                STATUS mandatory
                DESCRIPTION
                    "The status of the server.  Set to 'invalid' to 
                    remove the entry."

            
            
            
            
            
            
                DEFVAL { valid }
                ::= { udpBcstServerEntry 2 }
            
            udpBcstPortTbl OBJECT-TYPE
                SYNTAX SEQUENCE OF UdpBcstPortEntry
                ACCESS not-accessible
                STATUS mandatory
                DESCRIPTION
                    "Table of incoming UDP destination port numbers for 
                    which UDP broadcasts will be forwarded."
                ::= { routerUdp 2 }
            
            udpBcstPortEntry OBJECT-TYPE
                SYNTAX UdpBcstPortEntry
                ACCESS not-accessible
                STATUS mandatory
                DESCRIPTION
                    "A particular entry."
                INDEX { udpBcstPort }
                ::= { udpBcstPortTbl 1 }
            
            UdpBcstPortEntry ::=
                SEQUENCE {
                    udpBcstPort
                        INTEGER,
                    udpBcstPortStatus
                        INTEGER
                }
            
            udpBcstPort OBJECT-TYPE
                SYNTAX INTEGER
                ACCESS read-write
                STATUS mandatory
                DESCRIPTION
                    "The incoming destination UDP port number."
                ::= { udpBcstPortEntry 1 }
            
            udpBcstPortStatus OBJECT-TYPE
                SYNTAX INTEGER { invalid(1), valid(2) }
                ACCESS read-write
                STATUS mandatory
                DESCRIPTION
                    "The status of broadcast forwarding for the port.  
                    Set to 'invalid' to remove the entry."
                DEFVAL { valid }
                ::= { udpBcstPortEntry 2 }

            
            
            
            
            
            
            













































            
            
            
            
            
            
            -- the Router Policy group
            
            -- Implementation of this group is mandatory for all Xyplex
            -- systems that implement routing policy and do through
            -- routing
            
            -- the Router Policy group contains two subgroups:
            
            import OBJECT IDENTIFIER ::= { routerPolicy 1 }
            export OBJECT IDENTIFIER ::= { routerPolicy 2 }
            
            -- the Import subgroup
            
            impEgpTable OBJECT-TYPE
                SYNTAX SEQUENCE OF ImpEgpRule
                ACCESS not-accessible
                STATUS mandatory
                DESCRIPTION
                    "The EGP import table."
                ::= { import 1 }
            
            impEgpRule OBJECT-TYPE
                SYNTAX ImpEgpRule
                ACCESS not-accessible
                STATUS mandatory
                DESCRIPTION
                    "An EGP import rule.  Each rule is keyed by the 
                    Autonomous System of the EGP neighbor and the IP 
                    network of the route learned from the  neighbor.  
                    The AS can be set to a wild card as can the IP 
                    network. When a route is learned from a neighbor, 
                    the most specific import rule is applied to the 
                    route.  The route is either accepted or discarded 
                    and its metrics are applied according to the rule.  
                    An exact match on the AS and IP network is the most 
                    exact rule.  An exact match on the AS and a wild 
                    card match on the IP network is the 2nd most exact 
                    rule. A wild card match on the AS and an exact match 
                    on the IP network is the 3rd most exact match.  
                    Finally, a total wild card match is the least exact 
                    rule."
                INDEX { impEgpRuleAs, impEgpRuleNetwork }
                ::= { impEgpTable 1 }
            
            ImpEgpRule ::=
                SEQUENCE { 

            
            
            
            
            
            
                    impEgpRuleAs
                        INTEGER,
                    impEgpRuleNetwork
                        IpAddress,
                    impEgpRuleAction
                        INTEGER,
                    impEgpRulePreference
                        INTEGER,
                    impEgpRuleType
                        INTEGER,
                    impEgpRuleMetricAction
                        INTEGER,
                    impEgpRuleMetric
                        INTEGER,
                    impEgpRuleStatus
                        INTEGER
                }
            
            impEgpRuleAs OBJECT-TYPE
                SYNTAX INTEGER ( 0..65535 )
                ACCESS read-only
                STATUS mandatory
                DESCRIPTION
                    "The Autonomous System of the neighbor.  The value 
                    65535 is a wild card matching any AS number."
                ::= { impEgpRule 1 }
            
            impEgpRuleNetwork OBJECT-TYPE
                SYNTAX IpAddress
                ACCESS read-only
                STATUS mandatory
                DESCRIPTION
                    "The IP network learned from the neighbor.  The 
                    value 255.255.255.255 is a wild card matching any 
                    network."
                ::= { impEgpRule 2 }
            
            impEgpRuleAction OBJECT-TYPE
                SYNTAX INTEGER { discard(1), accept(2) }
                ACCESS read-write
                STATUS mandatory
                DESCRIPTION
                    "Control whether the route is learned or 
                    discarded."
                DEFVAL { accept }
                ::= { impEgpRule 3 }

            
            
            
            
            
            
            
            impEgpRulePreference OBJECT-TYPE
                SYNTAX INTEGER ( 1..255 )
                ACCESS read-write
                STATUS mandatory
                DESCRIPTION
                    "Preference to be stored with the route. The lower 
                    preference is preferred."
                DEFVAL { 2 }
                ::= { impEgpRule 4 }
            
            impEgpRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impEgpRule 5 }
            
            impEgpRuleMetricAction OBJECT-TYPE
                SYNTAX INTEGER { replace(1), increment(2),
                                 decrement(3) }
                ACCESS read-write
                STATUS mandatory
                DESCRIPTION
                    "How to apply the impEgpRuleMetric field to the 
                    metric learned with the route before storing it in 
                    the routing table."
                DEFVAL { increment }
                ::= { impEgpRule 6 }
            
            impEgpRuleMetric OBJECT-TYPE
                SYNTAX INTEGER (0..65535)
                ACCESS read-write
                STATUS mandatory
                DESCRIPTION
                    "Metric value to be applied to the metric learned 
                    learned with the route before storing it in the 
                    routing table."
                DEFVAL { 0 }
                ::= { impEgpRule 7 }
            
            impEgpRuleStatus OBJECT-TYPE

            
            
            
            
            
            
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impEgpRule 8 }
            
            impOspfTable OBJECT-TYPE
                SYNTAX SEQUENCE OF ImpOspfRule
                ACCESS not-accessible
                STATUS mandatory
                DESCRIPTION
                    "The OSPF import table."
                ::= { import 2 }
            
            impOspfRule OBJECT-TYPE
                SYNTAX ImpOspfRule
                ACCESS not-accessible
                STATUS mandatory
                DESCRIPTION
                    "An OSPF import rule.  Each rule is keyed by the IP 
                    network of the route and the AS from which it was 
                    learned.  The Ip network and the AS can both be set 
                    to a wild card.  When an OSPF route is added to the 
                    routing table, the most specific import rule is 
                    applied to set the preference of the route.  An 
                    exact match on the Ip network and on the AS is the 
                    most exact rule.  An exact match on the IP network 
                    and a wild card match on the AS is the 2nd most 
                    exact rule.  A wild card match on both the  on the 
                    AS and IP network is the next and least exact 
                    rule."
                INDEX { impOspfRuleNetwork }
                ::= { impOspfTable 1 }
            
            ImpOspfRule ::=
                SEQUENCE {
                    impOspfRuleNetwork
                        IpAddress,
                    impOspfRulePreference
                        INTEGER,
                    impOspfRuleStatus
                        INTEGER

            
            
            
            
            
            
                }
            
            impOspfRuleNetwork OBJECT-TYPE
                SYNTAX IpAddress
                ACCESS read-only
                STATUS mandatory
                DESCRIPTION
                    "The IP network of the route.  The value 
                    255.255.255.255 is a wild card matching any 
                    network."
                ::= { impOspfRule 1 }
            
            impOspfRulePreference OBJECT-TYPE
                SYNTAX INTEGER ( 1..255 )
                ACCESS read-write
                STATUS mandatory
                DESCRIPTION
                    "Preference to be stored with the route. The lower 
                    preference is preferred."
                DEFVAL { 8 }
                ::= { impOspfRule 2 }
            
            impOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impOspfRule 3 }














            
            
            
            
            
            
            -- the Export subgroup
            
            expEgpToEgpTable OBJECT-TYPE
                SYNTAX SEQUENCE OF ExpEgpToEgpRule
                ACCESS not-accessible
                STATUS mandatory
                DESCRIPTION
                    "The EGP to EGP export table."
                ::= { export 1 }
            
            expEgpToEgpRule OBJECT-TYPE
                SYNTAX ExpEgpToEgpRule
                ACCESS not-accessible
                STATUS mandatory
                DESCRIPTION
                    "An EGP to EGP export rule.  Each rule is keyed by 
                    the Autonomous  System of the EGP neighbor, the IP 
                    network of the EGP route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows: 
            
                            To As  IP Network     From AS  Rank
            
                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expEgpToEgpRuleToAs, expEgpToEgpRuleNetwork,
                        expEgpToEgpRuleFromAs }
                ::= { expEgpToEgpTable 1 }
            
            ExpEgpToEgpRule ::=
                SEQUENCE {
                    expEgpToEgpRuleToAs
                        INTEGER,
                    expEgpToEgpRuleNetwork

            
            
            
            
            
            
                        IpAddress,
                    expEgpToEgpRuleFromAs
                        INTEGER,
                    expEgpToEgpRuleAction
                        INTEGER,
                    expEgpToEgpRuleMetricAction
                        INTEGER,
                    expEgpToEgpRuleMetric
                        INTEGER,
                    expEgpToEgpRuleStatus
                        INTEGER
                }
            
            expEgpToEgpRuleToAs OBJECT-TYPE
                SYNTAX INTEGER ( 0..65535 )
                ACCESS read-only
                STATUS mandatory
                DESCRIPTION
                    "The Autonomous System of the neighbor.  The value 
                    65535 is  a wild card matching any AS number."
                ::= { expEgpToEgpRule 1 }
            
            expEgpToEgpRuleNetwork OBJECT-TYPE
                SYNTAX IpAddress 
                ACCESS read-only
                STATUS mandatory
                DESCRIPTION
                    "The IP network of the route in the route table.  
                    The value 255.255.255.255 is a wild card matching 
                    any network."
                ::= { expEgpToEgpRule 2 }
            
            expEgpToEgpRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToEgpRule 3 }
            
            expEgpToEgpRuleAction OBJECT-TYPE
                SYNTAX INTEGER { hide(1), advertise(2) }
                ACCESS read-write
                STATUS mandatory

            
            
            
            
            
            
                DESCRIPTION
                    "Control whether the route is advertised or not."
                DEFVAL { advertise }
                ::= { expEgpToEgpRule 4 }
            
            expEgpToEgpRuleMetricAction OBJECT-TYPE
                SYNTAX INTEGER { replace(1), increment(2),
                                 decrement(3) }
                ACCESS read-write
                STATUS mandatory
                DESCRIPTION
                    "How to apply the expEgpToEgpRuleMetric field to the 
                    metric in the route table entry before the route is 
                    advertised."
                DEFVAL { increment }
                ::= { expEgpToEgpRule 5 }
            
            expEgpToEgpRuleMetric OBJECT-TYPE
                SYNTAX INTEGER (0..65535)
                ACCESS read-write
                STATUS mandatory
                DESCRIPTION
                    "Metric value to be applied to the metric in the 
                    route table entry before the route is advertised."
                DEFVAL { 0 }
                ::= { expEgpToEgpRule 6 }
            
            expEgpToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToEgpRule 7 }
            
            -- ospf to egp
            
            expOspfToEgpTable OBJECT-TYPE
                SYNTAX SEQUENCE OF ExpOspfToEgpRule
                ACCESS not-accessible
                STATUS mandatory
                DESCRIPTION
                    "The OSPF to EGP export table."

            
            
            
            
            
            
                ::= { export 2 }
            
            expOspfToEgpRule OBJECT-TYPE
                SYNTAX ExpOspfToEgpRule
                ACCESS not-accessible
                STATUS mandatory
                DESCRIPTION
                    "An OSPF to EGP export rule.  Each rule is keyed by 
                    the Autonomous  System of the EGP neighbor, the IP 
                    network of the OSPF route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows:
            
                            To As  IP Network     From AS  Rank
            
                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expOspfToEgpRuleToAs, expOspfToEgpRuleNetwork,
                        expOspfToEgpRuleFromAs }
                ::= { expOspfToEgpTable 1 }
            
            ExpOspfToEgpRule ::=
                SEQUENCE {
                    expOspfToEgpRuleToAs
                        INTEGER,
                    expOspfToEgpRuleNetwork
                        IpAddress,
                    expOspfToEgpRuleFromAs
                        INTEGER,
                    expOspfToEgpRuleAction
                        INTEGER,
                    expOspfToEgpRuleMetricAction
                        INTEGER,
                    expOspfToEgpRuleMetric

            
            
            
            
            
            
                        INTEGER,
                    expOspfToEgpRuleStatus
                        INTEGER
                }
            
            expOspfToEgpRuleToAs OBJECT-TYPE
                SYNTAX INTEGER ( 0..65535 )
                ACCESS read-only
                STATUS mandatory
                DESCRIPTION
                    "The Autonomous System of the neighbor.  The value 
                    65535 is  a wild card matching any AS number."
                ::= { expOspfToEgpRule 1 }
            
            expOspfToEgpRuleNetwork OBJECT-TYPE
                SYNTAX IpAddress
                ACCESS read-only
                STATUS mandatory
                DESCRIPTION
                    "The IP network of the route in the route table.  
                    The value 255.255.255.255 is a wild card matching 
                    any network."
                ::= { expOspfToEgpRule 2 }
            
            expOspfToEgpRuleFromAs OBJECT-TYPE
                SYNTAX INTEGER ( 0..65535 )
                ACCESS read-only
                STATUS mandatory
                DESCRIPTION
                    "The Autonomous System of the route in the route 
                    table.  Local indicates that the route was not an 
                    external OSPF route.  The  value 65535 is a wild 
                    card matching any AS number, and the value 65534 is 
                    for routes within the local AS."
                ::= { expOspfToEgpRule 3 }
            
            expOspfToEgpRuleAction OBJECT-TYPE
                SYNTAX INTEGER { hide(1), advertise(2) }
                ACCESS read-write
                STATUS mandatory
                DESCRIPTION
                    "Control whether the route is advertised or not."
                DEFVAL { advertise }
                ::= { expOspfToEgpRule 4 }
            
            expOspfToEgpRuleMetricAction OBJECT-TYPE

            
            
            
            
            
            
                SYNTAX INTEGER { replace(1), increment(2),
                                 decrement(3) }
                ACCESS read-write
                STATUS mandatory
                DESCRIPTION
                    "How to apply the expOspfToEgpRuleMetric field to 
                    the metric in the route table entry before the route 
                    is advertised."
                DEFVAL { increment }
                ::= { expOspfToEgpRule 5 }
            
            expOspfToEgpRuleMetric OBJECT-TYPE
                SYNTAX INTEGER (0..65535)
                ACCESS read-write
                STATUS mandatory
                DESCRIPTION
                    "Metric value to be applied to the metric in the 
                    route table entry before the route is advertised."
                DEFVAL { 0 }
                ::= { expOspfToEgpRule 6 }
            
            expOspfToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expOspfToEgpRule 7 }
            
            -- static to egp
            
            expStaticToEgpTable OBJECT-TYPE
                SYNTAX SEQUENCE OF ExpStaticToEgpRule
                ACCESS not-accessible
                STATUS mandatory
                DESCRIPTION
                    "The Static to EGP export table."
                ::= { export 3 }
            
            expStaticToEgpRule OBJECT-TYPE
                SYNTAX ExpStaticToEgpRule
                ACCESS not-accessible
                STATUS mandatory

            
            
            
            
            
            
                DESCRIPTION
                    "An Static to EGP export rule.  Each rule is keyed 
                    by the Autonomous  System of the EGP neighbor and 
                    the IP network of the Static route in the  routing 
                    table.  The neighbor (to) AS can be set to a wild 
                    card as can the IP network.  The route is either 
                    accepted to be advertised to the  neighbor or 
                    discarded from being advertised, and its metric is 
                    applied  according to the rule.  The best match is 
                    as follows:
            
                            To As  IP Network  Rank
            
                            exact       exact   1st
                            exact   wild card   2nd
                        wild card       exact   3rd
                        wild card   wild card   4th
                    "
                INDEX { expStaticToEgpRuleToAs,
                        expStaticToEgpRuleNetwork }
                ::= { expStaticToEgpTable 1 }
            
            ExpStaticToEgpRule ::=
                SEQUENCE {
                    expStaticToEgpRuleToAs
                        INTEGER,
                    expStaticToEgpRuleNetwork
                        IpAddress,
                    expStaticToEgpRuleAction
                        INTEGER,
                    expStaticToEgpRuleMetricAction
                        INTEGER,
                    expStaticToEgpRuleMetric
                        INTEGER,
                    expStaticToEgpRuleStatus
                        INTEGER
                }
            
            expStaticToEgpRuleToAs OBJECT-TYPE
                SYNTAX INTEGER ( 0..65535 )
                ACCESS read-only
                STATUS mandatory
                DESCRIPTION
                    "The Autonomous System of the neighbor.  The value 
                    65535 is  a wild card matching any AS number."
                ::= { expStaticToEgpRule 1 }

            
            
            
            
            
            
            
            expStaticToEgpRuleNetwork OBJECT-TYPE
                SYNTAX IpAddress
                ACCESS read-only
                STATUS mandatory
                DESCRIPTION
                    "The IP network of the route in the route table.  
                    The value 255.255.255.255 is a wild card matching 
                    any network."
                ::= { expStaticToEgpRule 2 }
            
            expStaticToEgpRuleAction OBJECT-TYPE
                SYNTAX INTEGER { hide(1), advertise(2) }
                ACCESS read-write
                STATUS mandatory
                DESCRIPTION
                    "Control whether the route is advertised or not."
                DEFVAL { advertise }
                ::= { expStaticToEgpRule 3 }
            
            expStaticToEgpRuleMetricAction OBJECT-TYPE
                SYNTAX INTEGER { replace(1), increment(2),
                                 decrement(3) }
                ACCESS read-write
                STATUS mandatory
                DESCRIPTION
                    "How to apply the expStaticToEgpRuleMetric field to 
                    the metric in the route table entry before the route 
                    is advertised."
                DEFVAL { increment }
                ::= { expStaticToEgpRule 4 }
            
            expStaticToEgpRuleMetric OBJECT-TYPE
                SYNTAX INTEGER (0..65535)
                ACCESS read-write
                STATUS mandatory
                DESCRIPTION
                    "Metric value to be applied to the metric in the 
                    route table entry before the route is advertised."
                DEFVAL { 0 }
                ::= { expStaticToEgpRule 5 }
            
            expStaticToEgpRuleStatus OBJECT-TYPE
                SYNTAX INTEGER { invalid(1), valid(2) }
                ACCESS read-write
                STATUS mandatory

            
            
            
            
            
            
                DESCRIPTION
                    "The status of the rule.  Set to 'invalid' to remove 
                    the rule.  If the all wild card rule is removed, it 
                    is  automatically readded with default values."
                DEFVAL { valid }
                ::= { expStaticToEgpRule 6 }
            
            -- egp to ospf
            
            expEgpToOspfTable OBJECT-TYPE
                SYNTAX SEQUENCE OF ExpEgpToOspfRule
                ACCESS not-accessible
                STATUS mandatory
                DESCRIPTION
                    "The EGP to OSPF export table."
                ::= { export 4 }
            
            expEgpToOspfRule OBJECT-TYPE
                SYNTAX ExpEgpToOspfRule
                ACCESS not-accessible
                STATUS mandatory
                DESCRIPTION
                    "An EGP to OSPF export rule.  Each rule is keyed by 
                    the IP network  of the EGP route in the routing 
                    table, and the Autonomous System  from which the 
                    route was learned.  The Ip network can be set to a 
                    wild card as can the (from) AS.  The route is either 
                    accepted to be  advertised to the neighbor or 
                    discarded from being advertised, and its metric is 
                    applied according to the rule.  The best match is as  
                    follows:
            
                       IP Network     From AS  Rank
            
                            exact       exact   1st
                            exact   wild card   2nd
                        wild card       exact   3rd
                        wild card   wild card   4th
                    "
                INDEX { expEgpToOspfRuleNetwork, expEgpToOspfRuleFromAs }
                ::= { expEgpToOspfTable 1 }
            
            ExpEgpToOspfRule ::=
                SEQUENCE {
                    expEgpToOspfRuleNetwork
                        IpAddress,

            
            
            
            
            
            
                    expEgpToOspfRuleFromAs
                        INTEGER,
                    expEgpToOspfRuleAction
                        INTEGER,
                    expEgpToOspfRuleStatus
                        INTEGER
                }
            
            expEgpToOspfRuleNetwork OBJECT-TYPE
                SYNTAX IpAddress
                ACCESS read-only
                STATUS mandatory
                DESCRIPTION
                    "The IP network of the route in the route table.  
                    The value 255.255.255.255 is a wild card matching 
                    any network."
                ::= { expEgpToOspfRule 1 }
            
            expEgpToOspfRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToOspfRule 2 }
            
            expEgpToOspfRuleAction OBJECT-TYPE
                SYNTAX INTEGER { hide(1), advertise(2) }
                ACCESS read-write
                STATUS mandatory
                DESCRIPTION
                    "Control whether the route is advertised or not."
                DEFVAL { advertise }
                ::= { expEgpToOspfRule 3 }
            
            expEgpToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }

            
            
            
            
            
            
                ::= { expEgpToOspfRule 4 }
            
END
