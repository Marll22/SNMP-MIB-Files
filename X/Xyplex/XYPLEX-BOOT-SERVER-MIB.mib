XYPLEX-BOOT-SERVER-MIB DEFINITIONS ::= BEGIN
            
                    IMPORTS
                            enterprises, Counter, Gauge
                                    FROM RFC1155-SMI
                            DisplayString
                                    FROM SNMPv2-TC
                            OBJECT-TYPE
                                    FROM RFC-1212
                            DateTime, AddressType
                                    FROM XYPLEX-SYSTEM-MIB;
            
            xyplex          OBJECT IDENTIFIER ::= { enterprises 33 }
            bootServer      OBJECT IDENTIFIER ::= { xyplex 6 }
            
            -- Xyplex Character subgroups
            
            bsBasic         OBJECT IDENTIFIER ::= { bootServer 1 }
            dump            OBJECT IDENTIFIER ::= { bootServer 2 }
            load            OBJECT IDENTIFIER ::= { bootServer 3 }
            param           OBJECT IDENTIFIER ::= { bootServer 4 }
            
            --  This MIB module uses the extended OBJECT-TYPE macro as
            --  defined in [9]
            
            --  this is the MIB module for providers of Xyplex
            --  bootstrap service

















            
            
            
            
            
            
            -- the Bootstrap Server Basic group
            
            -- Implementation of this group is mandatory for all Xyplex
            -- systems that provide the Xyplex bootstrap service
            
            basicLogLimit OBJECT-TYPE
                SYNTAX INTEGER (1..100)
                ACCESS read-write
                STATUS mandatory
                DESCRIPTION
                    "Maximum allowed number of kilobytes for recording 
                    events.  Corresponds directly to MANAGER LOG FILE 
                    SIZE and the value labeled 'Log File Size:' in the 
                    MANAGER CHARACTERISTICS display."
                ::= { bsBasic 1 }
            
            basicActiveLimit OBJECT-TYPE
                SYNTAX INTEGER (0..32)
                ACCESS read-write
                STATUS mandatory
                DESCRIPTION
                    "Maximum allowed number of simultaneous service 
                    dialogs.  Corresponds directly to MANAGER 
                    SIMULTANEOUS and the value labeled 'Maximum 
                    simultaneous requests:' in the MANAGER 
                    CHARACTERISTICS display."
                ::= { bsBasic 2 }
            
            basicActiveNumber OBJECT-TYPE
                SYNTAX Gauge
                ACCESS read-only
                STATUS mandatory
                DESCRIPTION
                    "Number of active service dialogs.  Corresponds 
                    indirectly to the list of active clients in the 
                    MANAGER STATUS display."
                ::= { bsBasic 3 }
            
            basicClientNumber OBJECT-TYPE
                SYNTAX Gauge
                ACCESS read-only
                STATUS mandatory
                DESCRIPTION
                    "Number of defined clients.  Corresponds indirectly 
                    to the list of defined clients in the MANAGER LOCAL, 
                    MANAGER GLOBAL, and MANAGER NODE displays."

            
            
            
            
            
            
                ::= { bsBasic 4 }
            
            basicOffersSent OBJECT-TYPE
                SYNTAX Counter
                ACCESS read-only
                STATUS mandatory
                DESCRIPTION
                    "Total number of service offers sent in response to 
                    client requests.  Corresponds directly to the value 
                    labeled 'Total service offers sent:' in the MANAGER 
                    STATUS display."
                ::= { bsBasic 5 }
            
            basicEventTotal OBJECT-TYPE
                SYNTAX Gauge
                ACCESS read-only
                STATUS mandatory
                DESCRIPTION
                    "Total number of events that have been written to 
                    the event log since it was last purged.  This may be 
                    less than the number currently in the log.  
                    Corresponds directly to the value labeled 'Total 
                    Messages Logged:' in the MANAGER EVENTS display."
                ::= { bsBasic 6 }
            
            basicEventPurge OBJECT-TYPE
                SYNTAX INTEGER { ready(1), execute(2) }
                ACCESS read-write
                STATUS mandatory
                DESCRIPTION
                    "Control to cause emptying the event log.  In 
                    response to a get-request or get-next-request, the 
                    agent always returns 'ready' for this value.  
                    Setting the value to 'ready' has no effect.  Setting 
                    it to 'execute' causes the event log to immediately 
                    become empty.  Corresponds directly to the PURGE 
                    MANAGER LOG FILE command."
                ::= { bsBasic 7 }








            
            
            
            
            
            
            -- The Active table
            
            activeTable OBJECT-TYPE
                SYNTAX SEQUENCE OF ActiveEntry
                ACCESS not-accessible
                STATUS mandatory
                DESCRIPTION
                    "A list of active client dialog entries.  The number 
                    of entries is given by basicActiveNumber."
                ::= { bsBasic 8 }
            
            activeEntry OBJECT-TYPE
                SYNTAX ActiveEntry
                ACCESS not-accessible
                STATUS mandatory
                DESCRIPTION
                    "Parameter values for an active client dialog 
                    entry."
                INDEX { activeIdentificationType, activeIdentification }
                ::= { activeTable 1 }
            
            ActiveEntry ::=
                SEQUENCE {
                    activeIdentificationType
                        AddressType,
                    activeIdentification
                        OCTET STRING,
                    activeFunction
                        INTEGER,
                    activeSoftwareVersionType
                        INTEGER,
                    activeSoftwareVersion
                        OCTET STRING,
                    activeParameterVersion
                        INTEGER,
                    activeCurrentSequence
                        INTEGER,
                    activeBytesRemaining
                        INTEGER,
                    activeFile
                        DisplayString,
                    activeStatus
                        INTEGER,
                    activeState
                        INTEGER
                }

            
            
            
            
            
            
            
            activeIdentificationType OBJECT-TYPE
                SYNTAX AddressType
                ACCESS read-only
                STATUS mandatory
                DESCRIPTION
                    "The type of identification value in 
                    activeIdentification.  Corresponds indirectly to the 
                    value labeled 'EthernetAddress' in the MANAGER 
                    STATUS display."
                ::= { activeEntry 1 }
            
            activeIdentification OBJECT-TYPE
                SYNTAX OCTET STRING (SIZE (1..6))
                ACCESS read-only
                STATUS mandatory
                DESCRIPTION
                    "Identification of the active partner.  Corresponds 
                    directly to the value labeled 'EthernetAddress' in 
                    the MANAGER STATUS display."
                ::= { activeEntry 2 }
            
            activeFunction OBJECT-TYPE
                SYNTAX INTEGER { parameterStore(1), load(2), dump(3),
                                 imageUpdate(4) }
                ACCESS read-only
                STATUS mandatory
                DESCRIPTION
                    "The function the server is performing with the 
                    partner.  Corresponds directly to the value labeled 
                    'Function' in the MANAGER STATUS display."
                ::= { activeEntry 3 }
            
            activeSoftwareVersionType OBJECT-TYPE
                SYNTAX INTEGER { alpha(1), beta(2),
                                 production(3), special(4),
                                 notApplicable(5) }
                ACCESS read-only
                STATUS mandatory
                DESCRIPTION
                    "If activeFunction is 'load', the software version 
                    being sent to the client, otherwise 'notApplicable'.  
                    Corresponds to the letter in the software version 
                    labeled 'Version' in the MANAGER STATUS display.
            
                    alpha         'A':   alpha test

            
            
            
            
            
            
                    beta          'B':   beta test
                    production    null:  normal, production software
                    special       'S':   special, custom software
                    "
                ::= { activeEntry 4 }
            
            activeSoftwareVersion OBJECT-TYPE
                SYNTAX OCTET STRING (SIZE (0..4))
                ACCESS read-only
                STATUS mandatory
                DESCRIPTION
                    "If activeFunction is 'load', the 4-byte software 
                    version being sent to the client, otherwise zero 
                    length.  In order, the octets contain major version, 
                    minor version, ECO, and pre-release number.  
                    Corresponds to the numbers in the software version 
                    labeled 'Version' in the MANAGER STATUS display.
            
                    For example, the version display for 
                    activeSoftwareVersionType 'production' and 
                    activeSoftwareVersion '2.2.0.0' is 'V2.2'.
            
                    The version display for activeSoftwareVersionType 
                    'beta' and activeSoftwareVersion '3.1.0.4' is 
                    'V3.1B4'."
                ::= { activeEntry 5 }
            
            activeParameterVersion OBJECT-TYPE
                SYNTAX INTEGER
                ACCESS read-only
                STATUS mandatory
                DESCRIPTION
                    "If activeFunction is 'parameterStore', the 
                    parameter version being stored by the client, 
                    otherwise zero.  Corresponds directly to the value 
                    labeled 'Version' in the MANAGER STATUS display."
                ::= { activeEntry 6 }
            
            activeCurrentSequence OBJECT-TYPE
                SYNTAX INTEGER
                ACCESS read-only
                STATUS mandatory
                DESCRIPTION
                    "The current dialog sequence number.  Corresponds 
                    directly to the value labeled 'Seq' in the MANAGER 
                    STATUS display."

            
            
            
            
            
            
                ::= { activeEntry 7 }
            
            activeBytesRemaining OBJECT-TYPE
                SYNTAX INTEGER
                ACCESS read-only
                STATUS mandatory
                DESCRIPTION
                    "The number of bytes remaining to be transferred in 
                    the dialog.  Corresponds directly to the value 
                    labeled 'Left' in the MANAGER STATUS display."
                ::= { activeEntry 8 }
            
            activeFile OBJECT-TYPE
                SYNTAX DisplayString (SIZE (1..16))
                ACCESS read-only
                STATUS mandatory
                DESCRIPTION
                    "The name of the file being used in the dialog.  
                    Corresponds directly to the value labeled 'File' in 
                    the MANAGER STATUS display."
                ::= { activeEntry 9 }
            
            activeStatus OBJECT-TYPE
                SYNTAX INTEGER { none(1),
                                 fileTooLarge(2),
                                 notImageFile(3),
                                 notExecutableFile(4),
                                 badFileData(5),
                                 deviceWriteProtected(6),
                                 operationTimeout(7),
                                 remoteFileNotFound(8),
                                 remoteFileAccessViolation(9),
                                 protocolError(10),
                                 fileSystemError(11),
                                 temporaryResourceConflict(12),
                                 success(13) }
                ACCESS read-only
                STATUS mandatory
                DESCRIPTION
                    "The final status of the most recent attempt to get 
                    an image.  Corresponds directly to the value labeled 
                    'Get Status:' in the DEVICE STATUS display."
                ::= { activeEntry 10 }
            
            activeState OBJECT-TYPE
                SYNTAX INTEGER { idle(1),

            
            
            
            
            
            
                                 internal1(2),
                                 internal2(3),
                                 openPartner(4),
                                 openFile(5),
                                 receivePartner(6),
                                 writeFile(7),
                                 closePartner(8),
                                 closeFile(9),
                                 cleanup(10),
                                 done(11),
                                 error(12) }
                ACCESS read-only
                STATUS mandatory
                DESCRIPTION
                    "The dynamic state of an active attempt to get an 
                    image.  Corresponds directly to the value labeled 
                    'Get State:' in the DEVICE STATUS display."
                ::= { activeEntry 11 }




























            
            
            
            
            
            
            -- The Client table
            
            clientTable OBJECT-TYPE
                SYNTAX SEQUENCE OF ClientEntry
                ACCESS not-accessible
                STATUS mandatory
                DESCRIPTION
                    "A list of client data base entries.  The number of 
                    entries is given by basicClientNumber."
                ::= { bsBasic 9 }
            
            clientEntry OBJECT-TYPE
                SYNTAX ClientEntry
                ACCESS not-accessible
                STATUS mandatory
                DESCRIPTION
                    "Parameter values for a client data base entry."
                INDEX { clientIdentificationType, clientIdentification }
                ::= { clientTable 1 }
            
            ClientEntry ::=
                SEQUENCE {
                    clientIdentificationType
                        AddressType,
                    clientIdentification
                        OCTET STRING,
                    clientEntryStatus
                        INTEGER,
                    clientName
                        DisplayString,
                    clientLoadFile
                        DisplayString,
                    clientDiagnosticFile
                        DisplayString,
                    clientLoadService
                        INTEGER,
                    clientDumpService
                        INTEGER
                }
            
            clientIdentificationType OBJECT-TYPE
                SYNTAX AddressType
                ACCESS read-write
                STATUS mandatory
                DESCRIPTION
                    "The type of identification value in 

            
            
            
            
            
            
                            clientIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 1 }
            
            clientIdentification OBJECT-TYPE
                SYNTAX OCTET STRING (SIZE (1..6))
                ACCESS read-write
                STATUS mandatory
                DESCRIPTION
                    "Identification of the client, either a hardware 
                    type or an Ethernet address, depending on 
                    clientIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 2 }
            
            clientEntryStatus OBJECT-TYPE
                SYNTAX INTEGER { invalid(1), valid(2) }
                ACCESS read-write
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { clientEntry 3 }
            
            clientName OBJECT-TYPE
                SYNTAX DisplayString (SIZE (0..16))
                ACCESS read-write
                STATUS mandatory
                DESCRIPTION
                    "A name that may be used to identify the client.  
                    Corresponds directly to the value labeled 'Name' in 
                    the MANAGER NODE display."
                DEFVAL { "" }
                ::= { clientEntry 4 }

            
            
            
            
            
            
            
            clientLoadFile OBJECT-TYPE
                SYNTAX DisplayString (SIZE (0..16))
                ACCESS read-write
                STATUS mandatory
                DESCRIPTION
                    "The file with the client's load image.  Corresponds 
                    directly to the value labeled 'Load File' in the 
                    MANAGER LOCAL, MANAGER GLOBAL, and MANAGER NODE 
                    displays."
                DEFVAL { "" }
                ::= { clientEntry 5 }
            
            clientDiagnosticFile OBJECT-TYPE
                SYNTAX DisplayString (SIZE (0..16))
                ACCESS read-write
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { clientEntry 6 }
            
            clientLoadService OBJECT-TYPE
                SYNTAX INTEGER { disabled(1), enabled(2) }
                ACCESS read-write
                STATUS mandatory
                DESCRIPTION
                    "Control for allowing load service for the client.  
                    Corresponds directly to the value labeled 'Load' in 
                    the MANAGER LOCAL, MANAGER GLOBAL, and MANAGER NODE 
                    displays."
                DEFVAL { enabled }
                ::= { clientEntry 7 }
            
            clientDumpService OBJECT-TYPE
                SYNTAX INTEGER { disabled(1), enabled(2) }
                ACCESS read-write
                STATUS mandatory
                DESCRIPTION
                    "Control for allowing dump service for the client.  
                    Corresponds directly to the value labeled 'Dump' in 
                    the MANAGER LOCAL, MANAGER GLOBAL, and MANAGER NODE 
                    displays."

            
            
            
            
            
            
                DEFVAL { disabled }
                ::= { clientEntry 8 }












































            
            
            
            
            
            
            -- The Named Client table
            
            -- This table is strict subset of the Client table, being
            -- the same information in the same form with client name
            -- as the table index instead of client identification.
            -- It does not contain clients that have no name.
            
            namedTable OBJECT-TYPE
                SYNTAX SEQUENCE OF NamedEntry
                ACCESS not-accessible
                STATUS mandatory
                DESCRIPTION
                    "A list of named client data base entries.  The 
                    number of entries is given by basicClientNumber."
                ::= { bsBasic 10 }
            
            namedEntry OBJECT-TYPE
                SYNTAX NamedEntry
                ACCESS not-accessible
                STATUS mandatory
                DESCRIPTION
                    "Parameter values for a named client data base 
                    entry."
                INDEX { namedName }
                ::= { namedTable 1 }
            
            NamedEntry ::=
                SEQUENCE {
                    namedIdentificationType
                        AddressType,
                    namedIdentification
                        OCTET STRING,
                    namedEntryStatus
                        INTEGER,
                    namedName
                        DisplayString,
                    namedLoadFile
                        DisplayString,
                    namedDiagnosticFile
                        DisplayString,
                    namedLoadService
                        INTEGER,
                    namedDumpService
                        INTEGER
                }
            

            
            
            
            
            
            
            namedIdentificationType OBJECT-TYPE
                SYNTAX AddressType
                ACCESS read-write
                STATUS mandatory
                DESCRIPTION
                    "The type of identification value in 
                    namedIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 1 }
            
            namedIdentification OBJECT-TYPE
                SYNTAX OCTET STRING (SIZE (1..6))
                ACCESS read-write
                STATUS mandatory
                DESCRIPTION
                    "Identification of the client, either a hardware 
                    type or an Ethernet address, depending on 
                    namedIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 2 }
            
            namedEntryStatus OBJECT-TYPE
                SYNTAX INTEGER { invalid(1), valid(2) }
                ACCESS read-write
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { namedEntry 3 }
            
            namedName OBJECT-TYPE
                SYNTAX DisplayString (SIZE (0..16))
                ACCESS read-write
                STATUS mandatory

            
            
            
            
            
            
                DESCRIPTION
                    "A name that may be used to identify the client.  
                    Corresponds directly to the value labeled 'Name' in 
                    the MANAGER NODE display."
                DEFVAL { "" }
                ::= { namedEntry 4 }
            
            namedLoadFile OBJECT-TYPE
                SYNTAX DisplayString (SIZE (0..16))
                ACCESS read-write
                STATUS mandatory
                DESCRIPTION
                    "The file with the client's load image.  Corresponds 
                    directly to the value labeled 'Load File' in the 
                    MANAGER LOCAL, MANAGER GLOBAL, and MANAGER NODE 
                    displays."
                DEFVAL { "" }
                ::= { namedEntry 5 }
            
            namedDiagnosticFile OBJECT-TYPE
                SYNTAX DisplayString (SIZE (0..16))
                ACCESS read-write
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { namedEntry 6 }
            
            namedLoadService OBJECT-TYPE
                SYNTAX INTEGER { disabled(1), enabled(2) }
                ACCESS read-write
                STATUS mandatory
                DESCRIPTION
                    "Control for allowing load service for the client.  
                    Corresponds directly to the value labeled 'Load' in 
                    the MANAGER LOCAL, MANAGER GLOBAL, and MANAGER NODE 
                    displays."
                DEFVAL { enabled }
                ::= { namedEntry 7 }
            
            namedDumpService OBJECT-TYPE
                SYNTAX INTEGER { disabled(1), enabled(2) }
                ACCESS read-write

            
            
            
            
            
            
                STATUS mandatory
                DESCRIPTION
                    "Control for allowing dump service for the client.  
                    Corresponds directly to the value labeled 'Dump' in 
                    the MANAGER LOCAL, MANAGER GLOBAL, and MANAGER NODE 
                    displays."
                DEFVAL { disabled }
                ::= { namedEntry 8 }






































            
            
            
            
            
            
            -- The Event table
            
            eventTable OBJECT-TYPE
                SYNTAX SEQUENCE OF EventEntry
                ACCESS not-accessible
                STATUS mandatory
                DESCRIPTION
                    "A list of event entries.  The number of entries is 
                    given by basicEventNumber."
                ::= { bsBasic 11 }
            
            eventEntry OBJECT-TYPE
                SYNTAX EventEntry
                ACCESS not-accessible
                STATUS mandatory
                DESCRIPTION
                    "Parameter values for a event entry."
                INDEX { eventIndex }
                ::= { eventTable 1 }
            
            EventEntry ::=
                SEQUENCE {
                    eventIndex
                        INTEGER,
                    eventText
                        DisplayString
                }
            
            eventIndex OBJECT-TYPE
                SYNTAX INTEGER
                ACCESS read-only
                STATUS mandatory
                DESCRIPTION
                    "In identification number for an event.  The value 1 
                    indicates the oldest event in the file, with 
                    subsequent numbers indicating sequential events.  
                    The event text for a given number may change as a 
                    circular event log wraps over its beginning.  
                    Corresponds directly to the relative position of an 
                    event in the MANAGER EVENTS display."
                ::= { eventEntry 1 }
            
            eventText OBJECT-TYPE
                SYNTAX DisplayString (SIZE (1..255))
                ACCESS read-only
                STATUS mandatory

            
            
            
            
            
            
                DESCRIPTION
                    "The text of the event, including date, time and 
                    other information.  Corresponds directly to the 
                    individual event text in the MANAGER EVENTS 
                    display."
                ::= { eventEntry 2 }








































            
            
            
            
            
            
            -- The Device table
            
            basicDeviceNumber OBJECT-TYPE
                SYNTAX INTEGER
                ACCESS read-only
                STATUS mandatory
                DESCRIPTION
                    "The system's number of mass-storage devices."
                ::= { bsBasic 12 }
            
            deviceTable OBJECT-TYPE
                SYNTAX SEQUENCE OF DeviceEntry
                ACCESS not-accessible
                STATUS mandatory
                DESCRIPTION
                    "A list of device entries.  The number of entries is 
                    given by basicDeviceNumber."
                ::= { bsBasic 13 }
            
            deviceEntry OBJECT-TYPE
                SYNTAX DeviceEntry
                ACCESS not-accessible
                STATUS mandatory
                DESCRIPTION
                    "Parameter values for a device entry."
                INDEX { deviceIndex }
                ::= { deviceTable 1 }
            
            DeviceEntry ::=
                SEQUENCE {
                    deviceIndex
                        INTEGER,
                    deviceName
                        DisplayString,
                    deviceDescr
                        DisplayString,
                    deviceOperation
                        INTEGER,
                    deviceFormat
                        INTEGER,
                    deviceProtection
                        INTEGER,
                    deviceFormatMedium
                        INTEGER,
                    deviceGetFile
                        INTEGER,

            
            
            
            
            
            
                    deviceGetFileHostIdentificationType
                        AddressType,
                    deviceGetFileHostIdentification
                        OCTET STRING,
                    deviceGetFileName
                        DisplayString
                }
            
            deviceIndex OBJECT-TYPE
                SYNTAX INTEGER
                ACCESS read-only
                STATUS mandatory
                DESCRIPTION
                    "In identification number for a device, in the range 
                    1 to basicDeviceNumber"
                ::= { deviceEntry 1 }
            
            deviceName OBJECT-TYPE
                SYNTAX DisplayString (SIZE (0..16))
                ACCESS read-only
                STATUS mandatory
                DESCRIPTION
                    "A name by which the device is known in other 
                    displays, such as 'C1' or 'D2'."
                ::= { deviceEntry 2 }
            
            deviceDescr OBJECT-TYPE
                SYNTAX DisplayString (SIZE (0..80))
                ACCESS read-only
                STATUS mandatory
                DESCRIPTION
                    "Details of the device type, including, for example, 
                    size, manufacturer, Flash versus RAM, and such.  
                    Corresponds directly to the value labeled 'Device 
                    Type: in the MANAGER DEVICE STATUS display."
                ::= { deviceEntry 3 }
            
            deviceOperation OBJECT-TYPE
                SYNTAX INTEGER { read(1), write(2), format(3), idle(4) }
                ACCESS read-only
                STATUS mandatory
                DESCRIPTION
                    "Current operational state of the device.  
                    Corresponds directly the value labeled 'Device 
                    Operation:' in the MANAGER DEVICE STATUS display."
                ::= { deviceEntry 4 }

            
            
            
            
            
            
            
            deviceFormat OBJECT-TYPE
                SYNTAX INTEGER { unformatted(1), formatted(2),
                                 unknown(3) }
                ACCESS read-only
                STATUS mandatory
                DESCRIPTION
                    "Formatting status of the device.  Corresponds 
                    directly the presence of one of the value labels 
                    under the label 'Device Status:' in the MANAGER 
                    DEVICE STATUS display."
                ::= { deviceEntry 5 }
            
            deviceProtection OBJECT-TYPE
                SYNTAX INTEGER { write-enabled(1), write-protected(2),
                                 unknown(3) }
                ACCESS read-only
                STATUS mandatory
                DESCRIPTION
                    "Write-protect status of the device.  Corresponds 
                    directly the presence of one of the value labels 
                    under the label 'Device Status:' in the MANAGER 
                    DEVICE STATUS display."
                ::= { deviceEntry 6 }
            
            deviceFormatMedium OBJECT-TYPE
                SYNTAX INTEGER { ready(1), execute(2) }
                ACCESS read-write
                STATUS mandatory
                DESCRIPTION
                    "Control to cause formatting of the medium in the 
                    device.  In response to a get-request or 
                    get-next-request, the agent always returns 'ready' 
                    for this value.  Setting the value to 'ready' has no 
                    effect.  Setting it to 'execute' causes the device 
                    to be formatted.  Corresponds directly to the FORMAT 
                    DEVICE command."
                ::= { deviceEntry 7 }
            
            deviceGetFile OBJECT-TYPE
                SYNTAX INTEGER { ready(1), execute(2) }
                ACCESS read-write
                STATUS mandatory
                DESCRIPTION
                    "Control to cause getting a file to the device from 
                    a remote host system.  In response to a get-request 

            
            
            
            
            
            
                            or get-next-request, the agent always returns 
                    'ready' for this value.  Setting the value to 
                    'ready' has no effect.  Setting it to 'execute' 
                    causes the get to be attempted.  Corresponds 
                    directly to the GET DEVICE command.
            
                    When set to 'execute', the objects 
                    deviceGetFileHostIdentificationType, 
                    deviceGetFileHostIdentification, and 
                    deviceGetFileName must be somewhere in the same set 
                    request message."
                ::= { deviceEntry 8 }
            
            deviceGetFileHostIdentificationType OBJECT-TYPE
                SYNTAX AddressType
                ACCESS read-write
                STATUS mandatory
                DESCRIPTION
                    "The type of identification value in 
                    deviceIdentification.  Corresponds indirectly to 
                    ADDRESS in the GET DEVICE command.
            
                    This object may not be set outside the context of 
                    setting deviceGetFile to 'execute'.  In response to 
                    a get-request or get-next-request, the value of this 
                    object is 'undefined'."
                ::= { deviceEntry 9 }
            
            deviceGetFileHostIdentification OBJECT-TYPE
                SYNTAX OCTET STRING (SIZE (1..6))
                ACCESS read-write
                STATUS mandatory
                DESCRIPTION
                    "Identification of the host to get the file from, 
                    with type depending on deviceIdentificationType.  
                    Corresponds directly to ADDRESS in the GET DEVICE 
                    command.
            
                    This object may not be set outside the context of 
                    setting deviceGetFile to 'execute'.  In response to 
                    a get-request or get-next-request, the value of this 
                    object is zero length."
                ::= { deviceEntry 10 }
            
            deviceGetFileName OBJECT-TYPE
                SYNTAX DisplayString (SIZE (1..64))

            
            
            
            
            
            
                ACCESS read-write
                STATUS mandatory
                DESCRIPTION
                    "The name of the file to get.  Corresponds directly 
                    to LOAD FILE in the GET DEVICE command.
            
                    This object may not be set outside the context of 
                    setting deviceGetFile to 'execute'.  In response to 
                    a get-request or get-next-request, the value of this 
                    object is zero length."
                ::= { deviceEntry 11 }



































            
            
            
            
            
            
            -- the Bootstrap Server Dump group
            
            -- Implementation of this group is mandatory for all Xyplex
            -- systems that provide the Xyplex bootstrap dump service
            
            dumpService OBJECT-TYPE
                SYNTAX INTEGER { disabled(1), enabled(2) }
                ACCESS read-write
                STATUS mandatory
                DESCRIPTION
                    "Control for allowing dump service for any client.  
                    Corresponds directly to DUMP and the value labeled 
                    'Dump:' in the MANAGER CHARACTERISTICS display."
                ::= { dump 1 }
            
            dumpDrive OBJECT-TYPE
                SYNTAX INTEGER (1..2)
                ACCESS read-write
                STATUS mandatory
                DESCRIPTION
                    "Identification number of the disk drive where dumps 
                    are stored.  Corresponds directly to DUMP DRIVE and 
                    the value labeled 'Dump Drive:' in the MANAGER 
                    CHARACTERISTICS display."
                ::= { dump 2 }
            
            dumpMerit OBJECT-TYPE
                SYNTAX INTEGER (0..15)
                ACCESS read-write
                STATUS mandatory
                DESCRIPTION
                    "Relative preference for this dump server over 
                    others.  Corresponds directly to DUMP MERIT and the 
                    value labeled 'Dump Merit:' in the MANAGER 
                    CHARACTERISTICS display."
                ::= { dump 3 }
            
            dumpSize OBJECT-TYPE
                SYNTAX INTEGER { small(1), full(2) }
                ACCESS read-write
                STATUS mandatory
                DESCRIPTION
                    "Type of dump file to keep.  Corresponds directly to 
                    DUMP SIZE and the value labeled 'Dump Size:' in the 
                    MANAGER CHARACTERISTICS display."
                ::= { dump 4 }

            
            
            
            
            
            
            
            dumpCompleted OBJECT-TYPE
                SYNTAX Counter
                ACCESS read-only
                STATUS mandatory
                DESCRIPTION
                    "The number of dumps completed since system 
                    initialization.  Corresponds directly to the value 
                    labeled 'Dump Operations Completed:' in the MANAGER 
                    STATUS display."
                ::= { dump 5 }
            
            dumpActive OBJECT-TYPE
                SYNTAX Gauge
                ACCESS read-only
                STATUS mandatory
                DESCRIPTION
                    "The number of dumps in progress.  Corresponds 
                    directly to the value labeled 'Currently Dumping:' 
                    in the MANAGER STATUS display."
                ::= { dump 6 }
            
            dumpFileNumber OBJECT-TYPE
                SYNTAX Gauge
                ACCESS read-only
                STATUS mandatory
                DESCRIPTION
                    "The number of dump files currently stored.  
                    Corresponds directly to the value labeled 'Network 
                    dump files' and 'files' in the MANAGER FILES 
                    display."
                ::= { dump 7 }














            
            
            
            
            
            
            -- The Dump File table
            
            dumpFileTable OBJECT-TYPE
                SYNTAX SEQUENCE OF DumpFileEntry
                ACCESS not-accessible
                STATUS mandatory
                DESCRIPTION
                    "A list of dump file entries.  The number of entries 
                    is given by dumpFileNumber."
                ::= { dump 8 }
            
            dumpFileEntry OBJECT-TYPE
                SYNTAX DumpFileEntry
                ACCESS not-accessible
                STATUS mandatory
                DESCRIPTION
                    "Parameter values for a dump file entry."
                INDEX { dumpFileIdentificationType,
                        dumpFileIdentification }
                ::= { dumpFileTable 1 }
            
            DumpFileEntry ::=
                SEQUENCE {
                    dumpFileIdentificationType
                        AddressType,
                    dumpFileIdentification
                        OCTET STRING,
                    dumpFileEntryStatus
                        INTEGER,
                    dumpFileCreation
                        DateTime,
                    dumpFileSize
                        INTEGER
                }
            
            dumpFileIdentificationType OBJECT-TYPE
                SYNTAX AddressType
                ACCESS read-only
                STATUS mandatory
                DESCRIPTION
                    "The type of identification value in 
                    dumpFileIdentification.  Corresponds indirectly to a 
                    file name part in the section labeled 'Network dump 
                    files' in the MANAGER FILES display."
                ::= { dumpFileEntry 1 }
            

            
            
            
            
            
            
            dumpFileIdentification OBJECT-TYPE
                SYNTAX OCTET STRING (SIZE (1..6))
                ACCESS read-only
                STATUS mandatory
                DESCRIPTION
                    "Identification of the dump file, an Ethernet 
                    address, as indicated by dumpFileIdentificationType.  
                    Corresponds indirectly to a file name part in the 
                    section labeled 'Network dump files' in the MANAGER 
                    FILES display."
                ::= { dumpFileEntry 2 }
            
            dumpFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER DUMP FILES command.  Actual 
                    removal of the entry is implementation specific."
                ::= { dumpFileEntry 3 }
            
            dumpFileCreation OBJECT-TYPE
                SYNTAX DateTime
                ACCESS read-only
                STATUS mandatory
                DESCRIPTION
                    "The time the dump file was created.  Corresponds 
                    directly to a date and time in the section labeled 
                    'Network dump files' in the MANAGER FILES display."
                ::= { dumpFileEntry 4 }
            
            dumpFileSize OBJECT-TYPE
                SYNTAX INTEGER
                ACCESS read-only
                STATUS mandatory
                DESCRIPTION
                    "The number of bytes stored in the dump file.  
                    Corresponds directly to the value labeled 'bytes' in 
                    the section labeled 'Network dump files' in the 
                    MANAGER FILES display."
                ::= { dumpFileEntry 5 }



            
            
            
            
            
            
            -- the Bootstrap Server Load group
            
            -- Implementation of this group is mandatory for all Xyplex
            -- systems that provide the Xyplex bootstrap load service
            
            loadService OBJECT-TYPE
                SYNTAX INTEGER { disabled(1), enabled(2) }
                ACCESS read-write
                STATUS mandatory
                DESCRIPTION
                    "Control for allowing load service for any client.  
                    Corresponds directly to LOAD and the value labeled 
                    'Load:' in the MANAGER CHARACTERISTICS display."
                ::= { load 1 }
            
            loadMerit OBJECT-TYPE
                SYNTAX INTEGER (0..15)
                ACCESS read-write
                STATUS mandatory
                DESCRIPTION
                    "Relative preference for this load server over 
                    others.  Corresponds directly to LOAD MERIT and the 
                    value labeled 'Load Merit:' in the MANAGER 
                    CHARACTERISTICS display."
                ::= { load 2 }
            
            loadCompleted OBJECT-TYPE
                SYNTAX Counter
                ACCESS read-only
                STATUS mandatory
                DESCRIPTION
                    "The number of loads completed since system 
                    initialization.  Corresponds directly to the value 
                    labeled 'Load Operations Completed:' in the MANAGER 
                    STATUS display."
                ::= { load 3 }
            
            loadActive OBJECT-TYPE
                SYNTAX Gauge
                ACCESS read-only
                STATUS mandatory
                DESCRIPTION
                    "The number of loads in progress.  Corresponds 
                    directly to the value labeled 'Currently Loading:' 
                    in the MANAGER STATUS display."
                ::= { load 4 }

            
            
            
            
            
            
            
            loadFileNumber OBJECT-TYPE
                SYNTAX Gauge
                ACCESS read-only
                STATUS mandatory
                DESCRIPTION
                    "The number of load files currently stored.  
                    Corresponds directly to the value labeled 'Load 
                    image files' and 'files' in the MANAGER FILES 
                    display."
                ::= { load 5 }



































            
            
            
            
            
            
            -- The Load File table
            
            loadFileTable OBJECT-TYPE
                SYNTAX SEQUENCE OF LoadFileEntry
                ACCESS not-accessible
                STATUS mandatory
                DESCRIPTION
                    "A list of load file entries.  The number of entries 
                    is given by loadFileNumber."
                ::= { load 6 }
            
            loadFileEntry OBJECT-TYPE
                SYNTAX LoadFileEntry
                ACCESS not-accessible
                STATUS mandatory
                DESCRIPTION
                    "Parameter values for a load file entry."
                INDEX { loadFileName }
                ::= { loadFileTable 1 }
            
            LoadFileEntry ::=
                SEQUENCE {
                    loadFileName
                        DisplayString,
                    loadFileCreation
                        DateTime,
                    loadFileSize
                        INTEGER,
                    loadFileSoftwareVersionType
                        INTEGER,
                    loadFileSoftwareVersion
                        OCTET STRING
                }
            
            loadFileName OBJECT-TYPE
                SYNTAX DisplayString (SIZE (1..16))
                ACCESS read-only
                STATUS mandatory
                DESCRIPTION
                    "The name of a load file.  Corresponds directly to a 
                    file name part in the section labeled 'Load image 
                    files' in the MANAGER FILES display."
                ::= { loadFileEntry 1 }
            
            loadFileCreation OBJECT-TYPE
                SYNTAX DateTime

            
            
            
            
            
            
                ACCESS read-only
                STATUS mandatory
                DESCRIPTION
                    "The time the load file was created.  Corresponds 
                    directly to a date and time in the section labeled 
                    'Load image files' in the MANAGER FILES display."
                ::= { loadFileEntry 2 }
            
            loadFileSize OBJECT-TYPE
                SYNTAX INTEGER
                ACCESS read-only
                STATUS mandatory
                DESCRIPTION
                    "The number of bytes stored in the load file.  
                    Corresponds directly to the value labeled 'bytes' in 
                    the section labeled 'Load image files' in the 
                    MANAGER FILES display."
                ::= { loadFileEntry 3 }
            
            loadFileSoftwareVersionType OBJECT-TYPE
                SYNTAX INTEGER { alpha(1), beta(2),
                                 production(3), special(4) }
                ACCESS read-only
                STATUS mandatory
                DESCRIPTION
                    "The software version type of the image in the load 
                    file.  Corresponds directly to a software version in 
                    the section labeled 'Load image files' in the 
                    MANAGER FILES display.
            
                    alpha         'A':   alpha test
                    beta          'B':   beta test
                    production    null:  normal, production software
                    special       'S':   special, custom software
                    "
                ::= { loadFileEntry 4 }
            
            loadFileSoftwareVersion OBJECT-TYPE
                SYNTAX OCTET STRING (SIZE (0..4))
                ACCESS read-only
                STATUS mandatory
                DESCRIPTION
                    "The software version of the image in the load file.  
                    Corresponds directly to a software version in the 
                    section labeled 'Load image files' in the MANAGER 
                    FILES display.

            
            
            
            
            
            
            
                    For example, the version display for 
                    loadFileSoftwareVersionType 'production' and 
                    loadFileSoftwareVersion '2.2.0.0' is 'V2.2'.
            
                    The version display for loadFileSoftwareVersionType 
                    'beta' and loadFileSoftwareVersion '3.1.0.4' is 
                    'V3.1B4'."
                ::= { loadFileEntry 5 }





































            
            
            
            
            
            
            -- the Bootstrap Server Parameter Storage group
            
            -- Implementation of this group is mandatory for all Xyplex
            -- systems that provide the Xyplex bootstrap parameter
            -- storage service
            
            paramService OBJECT-TYPE
                SYNTAX INTEGER { disabled(1), enabled(2) }
                ACCESS read-write
                STATUS mandatory
                DESCRIPTION
                    "Control for allowing parameter storage service for 
                    any client.  Corresponds directly to PARAMETER 
                    SERVICE and the value labeled 'Parameter Service:' 
                    in the MANAGER CHARACTERISTICS display."
                ::= { param 1 }
            
            paramDefaultService OBJECT-TYPE
                SYNTAX INTEGER { disabled(1), enabled(2) }
                ACCESS read-write
                STATUS mandatory
                DESCRIPTION
                    "Control for allowing default parameter loading 
                    service for any client.  Corresponds directly to 
                    PARAMETER DEFAULT SERVICE and the value labeled 
                    'Parameter Default Service:' in the MANAGER 
                    CHARACTERISTICS display."
                ::= { param 2 }
            
            paramDrive OBJECT-TYPE
                SYNTAX INTEGER (1..2)
                ACCESS read-write
                STATUS mandatory
                DESCRIPTION
                    "Identification number of the disk drive where 
                    parameters are stored.  Corresponds directly to 
                    PARAMETER DRIVE and the value labeled 'Parameter 
                    Drive:' in the MANAGER CHARACTERISTICS display."
                ::= { param 3 }
            
            paramActive OBJECT-TYPE
                SYNTAX Gauge
                ACCESS read-only
                STATUS mandatory
                DESCRIPTION
                    "The number of params in progress.  Corresponds 

            
            
            
            
            
            
                            directly to the value labeled 'Currently Paraming:' 
                    in the MANAGER STATUS display."
                ::= { param 4 }
            
            paramStorageActive OBJECT-TYPE
                SYNTAX Gauge
                ACCESS read-only
                STATUS mandatory
                DESCRIPTION
                    "The number of parameter storage operations in 
                    progress.  Corresponds directly to the value labeled 
                    'Currently saving parameters:' in the MANAGER STATUS 
                    display."
                ::= { param 5 }
            
            paramFileNumber OBJECT-TYPE
                SYNTAX Gauge
                ACCESS read-only
                STATUS mandatory
                DESCRIPTION
                    "The number of parameter files currently stored.  
                    Corresponds directly to the value labeled 'Parameter 
                    files' and 'files' in the MANAGER FILES display."
                ::= { param 6 }






















            
            
            
            
            
            
            -- The Param File table
            
            paramFileTable OBJECT-TYPE
                SYNTAX SEQUENCE OF ParamFileEntry
                ACCESS not-accessible
                STATUS mandatory
                DESCRIPTION
                    "A list of param file entries.  The number of 
                    entries is given by paramFileNumber."
                ::= { param 7 }
            
            paramFileEntry OBJECT-TYPE
                SYNTAX ParamFileEntry
                ACCESS not-accessible
                STATUS mandatory
                DESCRIPTION
                    "Parameter values for a param file entry."
                INDEX { paramFileIdentificationType,
                        paramFileIdentification }
                ::= { paramFileTable 1 }
            
            ParamFileEntry ::=
                SEQUENCE {
                    paramFileIdentificationType
                        AddressType,
                    paramFileIdentification
                        OCTET STRING,
                    paramFileEntryStatus
                        INTEGER,
                    paramFileWrite
                        DateTime,
                    paramFileSize
                        INTEGER,
                    paramFileParameterVersion
                        INTEGER
                }
            
            paramFileIdentificationType OBJECT-TYPE
                SYNTAX AddressType
                ACCESS read-only
                STATUS mandatory
                DESCRIPTION
                    "The type of identification value in 
                    paramFileIdentification.  Corresponds indirectly to 
                    a file name part in the section labeled 'Parameter 
                    files' in the MANAGER FILES display."

            
            
            
            
            
            
                ::= { paramFileEntry 1 }
            
            paramFileIdentification OBJECT-TYPE
                SYNTAX OCTET STRING (SIZE (1..6))
                ACCESS read-only
                STATUS mandatory
                DESCRIPTION
                    "Identification of the param file, an Ethernet 
                    address, as indicated by 
                    paramFileIdentificationType.  Corresponds indirectly 
                    to a file name part in the section labeled 
                    'Parameter files' in the MANAGER FILES display."
                ::= { paramFileEntry 2 }
            
            paramFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER PARAMETER FILES command.  Actual 
                    removal of the entry is implementation specific."
                ::= { paramFileEntry 3 }
            
            paramFileWrite OBJECT-TYPE
                SYNTAX DateTime
                ACCESS read-only
                STATUS mandatory
                DESCRIPTION
                    "The time the parameter file was last written.  
                    Corresponds directly to a date and time in the 
                    section labeled 'Parameter files' in the MANAGER 
                    FILES display."
                ::= { paramFileEntry 4 }
            
            paramFileSize OBJECT-TYPE
                SYNTAX INTEGER
                ACCESS read-only
                STATUS mandatory
                DESCRIPTION
                    "The number of bytes stored in the param file.  
                    Corresponds directly to the value labeled 'bytes' in 
                    the section labeled 'Parameter files' in the MANAGER 
                    FILES display."
                ::= { paramFileEntry 5 }

            
            
            
            
            
            
            
            paramFileParameterVersion OBJECT-TYPE
                SYNTAX INTEGER
                ACCESS read-only
                STATUS mandatory
                DESCRIPTION
                    "The version number of the parameter data in the 
                    file.  Corresponds directly to the value labeled 
                    'ver' in the section labeled 'Parameter files' in 
                    the MANAGER FILES display."
                ::= { paramFileEntry 6 }
            
END
