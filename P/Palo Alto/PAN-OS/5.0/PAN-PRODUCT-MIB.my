-- ***********************************************
-- PAN-PRODUCT-MIB.my
--
-- MIB for the platform specific MIB objects implemented by
-- Palo Alto devices.
-- ***********************************************

PAN-PRODUCTS-MIB DEFINITIONS ::= BEGIN

	IMPORTS
		MODULE-IDENTITY, OBJECT-IDENTITY,
		OBJECT-TYPE, NOTIFICATION-TYPE,
		Integer32
			FROM SNMPv2-SMI
--		MODULE-COMPLIANCE, OBJECT-GROUP
--			FROM SNMPv2-CONF
		DisplayString, TruthValue
			FROM SNMPv2-TC
		TcChassisType
			FROM PAN-GLOBAL-TC
		panModules, panProductsMibs
			FROM PAN-GLOBAL-REG;

	panProductsMibsModule MODULE-IDENTITY
		LAST-UPDATED			"201106271040Z"
		ORGANIZATION			"Palo Alto Networks"
		CONTACT-INFO			"
					Customer Support
					Palo Alto Networks
					3300 Olcott St.
					Santa Clara, CA 95054

					+1 866-898-9087
					support at paloaltonetworks dot com"

		DESCRIPTION				"
			A MIB module containing definitions of managed objects
			implemented by specific Palo Alto Networks' products."

		REVISION				"201102091610Z"
		DESCRIPTION				"
			Rev 1.0
			Initial version of MIB module PAN-PRODUCTS-MIB."

		::= { panModules 4 }

	panPA-4050 OBJECT-IDENTITY
		STATUS					current
		DESCRIPTION				"
			Sub-tree for PA-4050 specific objects."
		::= { panProductsMibs 1 }

	panPA-4020 OBJECT-IDENTITY
		STATUS					current
		DESCRIPTION				"
			Sub-tree for PA-4020 specific objects."
		::= { panProductsMibs 2 }

	panPA-2050 OBJECT-IDENTITY
		STATUS					current
		DESCRIPTION				"
			Sub-tree for PA-2050 specific objects."
		::= { panProductsMibs 3 }

	panPA-2020 OBJECT-IDENTITY
		STATUS					current
		DESCRIPTION				"
			Sub-tree for PA-2020 specific objects."
		::= { panProductsMibs 4 }

	panPA-4060 OBJECT-IDENTITY
		STATUS					current
		DESCRIPTION				"
			Sub-tree for PA-4060 specific objects."
		::= { panProductsMibs 5 }

	panPA-500 OBJECT-IDENTITY
		STATUS					current
		DESCRIPTION				"
			Sub-tree for PA-500 specific objects."
		::= { panProductsMibs 6 }

	panPanorama OBJECT-IDENTITY
		STATUS					current
		DESCRIPTION				"
			Sub-tree for Panorama specific objects."
		::= { panProductsMibs 7 }

	panPA-5060 OBJECT-IDENTITY
		STATUS					current
		DESCRIPTION				"
			Sub-tree for PA-5060 specific objects."
		::= { panProductsMibs 8 }

	panPA-5050 OBJECT-IDENTITY
		STATUS					current
		DESCRIPTION				"
			Sub-tree for PA-5050 specific objects."
		::= { panProductsMibs 9 }

	panPA-5020 OBJECT-IDENTITY
		STATUS					current
		DESCRIPTION				"
			Sub-tree for PA-5020 specific objects."
		::= { panProductsMibs 11 }

	panPA-200 OBJECT-IDENTITY
		STATUS					current
		DESCRIPTION				"
			Sub-tree for PA-200 specific objects."
		::= { panProductsMibs 12 }

	panPA-3050 OBJECT-IDENTITY
		STATUS					current
		DESCRIPTION				"
			Sub-tree for PA-3050 specific objects."
		::= { panProductsMibs 17 }

	panPA-3020 OBJECT-IDENTITY
		STATUS					current
		DESCRIPTION				"
			Sub-tree for PA-3020 specific objects."
		::= { panProductsMibs 18 }

	panPA-VM OBJECT-IDENTITY
		STATUS					current
		DESCRIPTION				"
			Sub-tree for PA-VM specific objects."
		::= { panProductsMibs 29 }

	panM-100 OBJECT-IDENTITY
		STATUS					current
		DESCRIPTION				"
			Sub-tree for M-100 specific objects."
		::= { panProductsMibs 30 }
	
END
