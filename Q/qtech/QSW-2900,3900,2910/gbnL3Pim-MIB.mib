GBNL3PIM-MIB DEFINITIONS ::= BEGIN

    IMPORTS
        MODULE-IDENTITY, OBJECT-TYPE,
        Integer32, Unsigned32                    FROM SNMPv2-SMI
        
        DisplayString, TruthValue,MacAddress,RowStatus    FROM SNMPv2-TC   
        InterfaceIndex                          FROM IF-MIB
                     
        MODULE-COMPLIANCE, OBJECT-GROUP         FROM SNMPv2-CONF
        
        gbnL3                                   FROM QTECH-MASTER-MIB;
    
        
    gbnL3PimMib MODULE-IDENTITY
        LAST-UPDATED    "0507040001Z"  -- July 04,2005  
        ORGANIZATION    "QTECH LLC"
        CONTACT-INFO    "Basil Budko
                         E-mail: budko@qtech.ru"

        DESCRIPTION     "NGBN Enterprise MIB definition."

        REVISION        "0507040001Z"  -- July 04,2005
        DESCRIPTION     "Initial MIB creation."

        ::= { gbnL3 8 }


   gbnL3PimGroup               OBJECT IDENTIFIER ::= { gbnL3PimMib 1 }   
    
   
    pimCommonTraceOption OBJECT-TYPE
        SYNTAX   Unsigned32
        MAX-ACCESS   read-write
        STATUS   current
        DESCRIPTION
           "PIM common trace option, including hello packet debug 
            switch and event debug switch andtimer debug switch"
           --PIM-DM和PIM-SM通用调试打印选项开关
      ::= { gbnL3PimGroup 1 }     
      
    pimDmTraceOption OBJECT-TYPE
        SYNTAX   Unsigned32
        MAX-ACCESS   read-write
        STATUS   current
        DESCRIPTION
           "PIM dense mode trace option"
           --PIM-DM调试打印选项开关
      ::= { gbnL3PimGroup 2 }       
      
   pimSmTraceOption OBJECT-TYPE
        SYNTAX   Unsigned32
        MAX-ACCESS   read-write
        STATUS   current
        DESCRIPTION
           "PIM sparse mode trace option"
           --PIM-SM调试打印选项开关
      ::= { gbnL3PimGroup 3 }           
           
    pimSourcePolicy OBJECT-TYPE
       SYNTAX   Integer32(1..99)
        MAX-ACCESS   read-write
        STATUS   current
        DESCRIPTION
           "Access control list(ACL) used for PIM multicast source"
      ::= { gbnL3PimGroup 4 }

    
--  PIM interface extra information

    pimInterfaceExtraTable OBJECT-TYPE
        SYNTAX   SEQUENCE OF PimInterfaceExtraEntry
        MAX-ACCESS   not-accessible
        STATUS   current
        DESCRIPTION
           "extra information of PIM interface"
       ::= { gbnL3PimMib 2 }

    pimInterfaceExtraEntry OBJECT-TYPE
        SYNTAX   PimInterfaceExtraEntry
        MAX-ACCESS   not-accessible
        STATUS   current
        DESCRIPTION
           "Extra information describing the configured  parame-
           ters  of interface."
       INDEX { pimInterfaceIndex }
       ::= { pimInterfaceExtraTable 1 }

    PimInterfaceExtraEntry ::=
	    SEQUENCE {
	        pimInterfaceIndex
	            InterfaceIndex,
	        pimInterfaceNeighborLimit
	            Integer32,
	        pimInterfaceNeighborPolicy
	            Integer32
	              }

    pimInterfaceIndex OBJECT-TYPE
        SYNTAX   InterfaceIndex
        MAX-ACCESS   read-only
        STATUS   current
        DESCRIPTION
           "PIM interface index"   
           --PIM接口索引
       ::= { pimInterfaceExtraEntry 1 }

    pimInterfaceNeighborLimit OBJECT-TYPE
        SYNTAX   Integer32(1..128)
        MAX-ACCESS   read-write
        STATUS   current
        DESCRIPTION
           "The max number of neighbors on this interface"    
           --一个接口上最多可以学习到的邻居数
       ::= { pimInterfaceExtraEntry 2 }

    pimInterfaceNeighborPolicy OBJECT-TYPE
        SYNTAX   Integer32(1..99)
        MAX-ACCESS   read-write
        STATUS   current
        DESCRIPTION
           "The neighbor filter, only neighbors which match the policy 
            can be thought valid."  
            --邻居访问控制列表号，标准访问控制列表1~99
       ::= { pimInterfaceExtraEntry 3 }


END
