GBNServiceCM-MIB DEFINITIONS ::= BEGIN

    IMPORTS
        MODULE-IDENTITY, OBJECT-TYPE,
        Integer32, IpAddress, 
        NOTIFICATION-TYPE                       FROM SNMPv2-SMI
        
        DisplayString, MacAddress,
        RowStatus, TruthValue                   FROM SNMPv2-TC
        
        MODULE-COMPLIANCE, OBJECT-GROUP         FROM SNMPv2-CONF
        
        gbnServiceAAA                           FROM QTECH-MASTER-MIB
        ;
        

    gbn8021xCmMib MODULE-IDENTITY
        LAST-UPDATED    "2002/07/02"  -- July 2, 2002
        ORGANIZATION    "QTECH LLC"
        CONTACT-INFO    "Basil Budko
                         E-mail: budko@qtech.ru"

        DESCRIPTION     "gbn CM Enterprise MIB definition."

        REVISION        "2002/07/02"  -- July 2, 2002
        DESCRIPTION     "Initial MIB creation."

        ::= { gbnServiceAAA 1 }


------------------------------------------------------------------------------
--  Textual Conventions (i.e., these do not affect object encoding):
------------------------------------------------------------------------------
    --
    --  "DURABLE":
    --    Objects that are saved across a system reset and/or power cycle
    --    are noted as "DURABLE" for convenience in the DESCRIPTION
    --    section of the object definition.  Code must be explicitly
    --    written to implement these DURABLE objects.
    --

------------------------------------------------------------------------------
--  define groups in GBN-8021xCM-MIB
------------------------------------------------------------------------------


        -------------------------------------------------------------------
        --Add gbn8021xCmConfTable MIB      2002/07/02     ouyangchunbo
        -------------------------------------------------------------------
        gbn8021xCmConfTable OBJECT-TYPE
        SYNTAX SEQUENCE OF gbn8021xCmConfEntry
        MAX-ACCESS not-accessible
        STATUS current
        DESCRIPTION
            "A Table of Radius configuration table"
        ::= { gbn8021xCmMib 1 }

        gbn8021xCmConfEntry OBJECT-TYPE
        SYNTAX gbn8021xCmConfEntry
        MAX-ACCESS not-accessible
        STATUS current
        DESCRIPTION
            "A list of radius parameters."
        INDEX { DomainIndex }
        ::= { gbn8021xCmConfTable 1 }

        gbn8021xCmConfEntry ::= SEQUENCE {
            DomainIndex    Integer32,
            DomainName     DisplayString,
            ServerName     DisplayString,
            MaxLinks       Integer32,
            CurrentLinks   Integer32,
            nActive        TruthValue,
            bCmUsed        TruthValue
        }

        DomainIndex OBJECT-TYPE
        SYNTAX Integer32 (1..1024)
        MAX-ACCESS not-accessible
        STATUS current
        DESCRIPTION
            "A simple index into 'gbn8021xCmConfTable'."
        ::= { gbn8021xCmConfEntry 1 }

        DomainName OBJECT-TYPE
        SYNTAX DisplayString (SIZE(1..24))
        MAX-ACCESS read-write
        STATUS current
        DESCRIPTION
            " A simple DomainName of gbn8021xCmConfEntry."
        ::= { gbn8021xCmConfEntry 2 }
        
        ServerName OBJECT-TYPE
        SYNTAX DisplayString (SIZE(1..32))
        MAX-ACCESS read-write
        STATUS current
        DESCRIPTION
            " A simple ServerName of gbn8021xCmConfEntry."
        ::= { gbn8021xCmConfEntry 3 }
        
        MaxLinks OBJECT-TYPE
        SYNTAX Integer32
        MAX-ACCESS read-write
        STATUS current
        DESCRIPTION
            "DURABLE: { 1024:all }
             A simple MaxLinks of  'gbn8021xCmConfTable'."
        ::= { gbn8021xCmConfEntry 4 }

        CurrentLinks OBJECT-TYPE
        SYNTAX Integer32
        MAX-ACCESS read-only
        STATUS current
        DESCRIPTION
             "A simple CurrentLinks of  'gbn8021xCmConfTable'."
        ::= { gbn8021xCmConfEntry 5 }

        nActive OBJECT-TYPE
        SYNTAX TruthValue
        MAX-ACCESS read-write
        STATUS current
        DESCRIPTION
             "Status of the current Domain 1-acitved  2 - unactived'."
        ::= { gbn8021xCmConfEntry 6 }


        bCmUsed OBJECT-TYPE
        SYNTAX TruthValue
        MAX-ACCESS read-write
        STATUS current
        DESCRIPTION
             "Status of the current Domain 1-used  2 - unused'."
        ::= { gbn8021xCmConfEntry 7 }


        gbn8021xEAPType OBJECT-TYPE
          SYNTAX Integer32 {
              eap-finish(1),
              eap-transfer(2)  
          }
        MAX-ACCESS read-write
        STATUS current
        DESCRIPTION
        "The operation form of EAP.
        eap-finish :Eap msg be processed in local device 
        eap-transfer:Eap msg will be transfered to RADIUS Server
        "
        ::= { gbn8021xCmMib 2 }
        

        defaultDomain OBJECT-TYPE
        SYNTAX DisplayString (SIZE(1..24))
        MAX-ACCESS read-write
        STATUS current
        DESCRIPTION
          " A simple default domain name."
        ::= { gbn8021xCmMib 3 }
        
--
-- END of GBN-8021xCM-MIB                
--

END
