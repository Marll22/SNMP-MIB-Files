GBNL2DhcpSnooping-MIB  DEFINITIONS ::= BEGIN

    IMPORTS
        MODULE-IDENTITY, OBJECT-TYPE,
        Integer32, Counter32,
        TimeTicks, IpAddress                    FROM SNMPv2-SMI
        DisplayString, TruthValue,RowStatus     FROM SNMPv2-TC
        
        MODULE-COMPLIANCE, OBJECT-GROUP         FROM SNMPv2-CONF
        
        gbnL2                                   FROM QTECH-MASTER-MIB;       
        
    gbnL3DhcpSnooping  MODULE-IDENTITY
        LAST-UPDATED    "0105030000Z"  -- May 03,2001  
        ORGANIZATION    "QTECH LLC"
        CONTACT-INFO    "Basil Budko
                         E-mail: budko@qtech.ru"

        DESCRIPTION     "GBN Enterprise MIB definition."

        REVISION        "0105030000Z"  -- May 03,2001
        DESCRIPTION     "Initial MIB creation."

        ::= { gbnL2 5 }

------------------------------------------------------------------------------
-- Textual Conventions (i.e., these do not affect object encoding):
------------------------------------------------------------------------------
    dhcpsnoopingOnOff OBJECT-TYPE
        SYNTAX       TruthValue
        MAX-ACCESS read-write
        STATUS current
        DESCRIPTION
            "start/stop dhcpsnooping.Default is off。" 
            --开启关闭Dhcpsnooping功能。
        ::= { gbnL3DhcpSnooping 1 }

    dhcpsnoopingPortTable OBJECT-TYPE
        SYNTAX      SEQUENCE OF DhcpsnoopingPortEntry
        MAX-ACCESS  not-accessible
        STATUS      current
        DESCRIPTION
            "A table that contains port informations of dhcpsnooping."
            --DHCPSnooping的端口信息表。
        ::= { gbnL3DhcpSnooping 2 }            
        
    dhcpsnoopingPortEntry OBJECT-TYPE
        SYNTAX      DhcpsnoopingPortEntry
        MAX-ACCESS  not-accessible
        STATUS      current
        DESCRIPTION
            "Port informations of dhcpsnooping. This is indexed
            by the port number."
            --DHCPSnooping的端口信息表，以端口号为索引。
        INDEX { portIndex }
        ::= { dhcpsnoopingPortTable 1 }
	
    DhcpsnoopingPortEntry ::=
    SEQUENCE {
        portIndex
           INTEGER,
        portTrustMode
           INTEGER,
        portMaxNum
           INTEGER
    }
     
    portIndex OBJECT-TYPE
        SYNTAX       INTEGER
        MAX-ACCESS   read-only
        STATUS       current
        DESCRIPTION
            "The Index of the port."
            --端口索引，也就是端口号
        ::= { dhcpsnoopingPortEntry 1 }    
        
    portTrustMode OBJECT-TYPE
    	SYNTAX INTEGER {
		trust(1),
		untrust(2)
	}
    MAX-ACCESS   read-write
    STATUS       current
    DESCRIPTION
        "Port mode of dhcpsnooping.Default is untrust."
        --端口模式，默认为untrust。
    ::= { dhcpsnoopingPortEntry 2 }

    portMaxNum OBJECT-TYPE
        SYNTAX INTEGER
        MAX-ACCESS read-write
        STATUS current
        DESCRIPTION
            "Max clients in this port.Range is from 0 to 2048.Default is 2048."
            --端口最多可以学习到的DHCP客户端，取值范围为0~2048。默认为2048。
        ::= { dhcpsnoopingPortEntry 3 }
    
    dhcpsnoopingVlanTable OBJECT-TYPE
        SYNTAX      SEQUENCE OF DhcpsnoopingVlanEntry
        MAX-ACCESS  not-accessible
        STATUS      current
        DESCRIPTION
            "A table that contains vlan informations of dhcpsnooping."
            --DHCPSnooping的VLAN信息表。
        ::= { gbnL3DhcpSnooping 3 }            
        
    dhcpsnoopingVlanEntry OBJECT-TYPE
        SYNTAX      DhcpsnoopingVlanEntry
        MAX-ACCESS  not-accessible
        STATUS      current
        DESCRIPTION
            "VLAN informations of dhcpsnooping. This is indexed
            by the vlan number."
            --DHCPSnooping的VLAN信息表，以VLAN号为索引。
        INDEX { vlanIndex }
        ::= { dhcpsnoopingVlanTable 1 }
	
    DhcpsnoopingVlanEntry ::=
    SEQUENCE {
        vlanIndex
           INTEGER,
        vlanMaxNum
           INTEGER
    }
    
    vlanIndex OBJECT-TYPE
        SYNTAX       INTEGER (1..4094)
        MAX-ACCESS   read-only
        STATUS       current
        DESCRIPTION
            "The Index of the port."
            --端口索引，也就是端口号
        ::= { dhcpsnoopingVlanEntry 1 }    
        

    vlanMaxNum OBJECT-TYPE
        SYNTAX INTEGER
        MAX-ACCESS read-write
        STATUS current
        DESCRIPTION
            "Max clients in this vlan.Range is from 0 to 2048.Default is 2048."
            --VLAN最多可以学习到的DHCP客户端，取值范围为0~2048。默认为2048。
        ::= { dhcpsnoopingVlanEntry 2 }                


END
