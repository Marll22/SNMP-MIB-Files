--  ************************************************
--  $Id: ZXR10-OPTICAL-INFO.mib 12 2008-10-07 09:01:17Z Fanhx $
--
--  ZXR10-OPTICAL-INFO.mib: ZXR10 ethnet query and  configuration MIB file
--  
--  Oct. 2008, Fan haixia
--   
--  Copyright(c) 2008 by ZTE Corporaton
--  All rights reservered
--
--  ************************************************

ZXR10OPTICALMIB DEFINITIONS ::= BEGIN

IMPORTS
    MODULE-IDENTITY, 
    OBJECT-TYPE, 
    Integer32   
        FROM SNMPv2-SMI
         
    zxr10interfaces
        FROM ZXR10-SMI;    
        
    zxr10OpticalMIB MODULE-IDENTITY
    LAST-UPDATED "200810070000Z"  -- October 07, 2008
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS v4.8.30 Optical info query and configuration MIB"
    ::= { zxr10interfaces 11 }

    DisplayString ::= OCTET STRING
    --  This data type is used to model textual information taken
    --  from the NVT ASCII character set.  By convention, objects
    --  with this syntax are declared as having
    --  SIZE (0..255)
  OpticalOnline ::= INTEGER 
            {
                  offline(0), 
                  online(1)              
            } 
   SonetComplianceCodesType ::=   
            INTEGER {
            	null(0),
   				short-reach(1),
   				intermediate-reach(2),
   				long-reach(4), 
   				very-Long-reach(8)           
            }  
   SonetComplianceCodesSpeed ::=    
            INTEGER {
            	oc3(1),
   				oc12(2),
   				oc48(4), 
   				oc192(8)           
            }
   GigabitEthernetComplianceCodesType ::=  
            INTEGER {
            	null(0),
   				base-sx-1000(1),
   				base-lx-1000(2),
   				base-lx-100(3),
   				base-cx-1000(4),
   				base-fx-100(5),
   				base-bx(6),
                base-px(7),
   				base-t-1000(8),
   				base-t-100(9)           
            }  

   InfinibandComplianceCodesType ::= 
            INTEGER {
            	null(0),
   				copper-Passiv(1),
   				copper-Active(2),
   				lx(4), 
   				sx(8)           
            }  
  GigabitEthernetComplianceCodesSpeed ::= 
            INTEGER {
            	m-1000(1),
   		        g-10(2),
   		        g-40(3),
   		        g-100(4)          
            }  
   InfinibandComplianceCodesSpeed ::= 
            INTEGER {
            	m-1000(1),
   		        g-10(2)         
            } 
-- Ethnet Optical Info table

    zxr10OpticalTable  OBJECT-TYPE
        SYNTAX  SEQUENCE OF Zxr10OpticalEntry
        MAX-ACCESS  not-accessible
        STATUS  current
        DESCRIPTION
            "Ethnet configuration table"
        ::= { zxr10OpticalMIB 1 }
        
   zxr10OpticalEntry  OBJECT-TYPE
        SYNTAX  Zxr10OpticalEntry
        MAX-ACCESS  not-accessible
        STATUS  current
        DESCRIPTION
            ""
        INDEX  { zxr10OpticalIfIndex }
        ::= { zxr10OpticalTable 1 }
          
   Zxr10OpticalEntry ::=
              SEQUENCE {
                zxr10OpticalIfIndex
                    Integer32,
                zxr10OpticalIfName
                    DisplayString,
                zxr10OpticalOnline
                    OpticalOnline,
                zxr10OpticalFpType
                    DisplayString,
                zxr10OpticalSonetComplianceCodesType
                    SonetComplianceCodesType, 
                zxr10OpticalSonetComplianceCodesSpeed
                    SonetComplianceCodesSpeed,  
                zxr10OpticalGigabitEthernetComplianceCodesType
                    DisplayString,                
                zxr10OpticalGigabitEthernetComplianceCodesSpeed
                    GigabitEthernetComplianceCodesSpeed,                
                zxr10OpticalInfinibandComplianceCodesType
                    InfinibandComplianceCodesType,             
                zxr10OpticalInfinibandComplianceCodesSpeed
                    InfinibandComplianceCodesSpeed,                              
                zxr10OpticalDisSMFkm
                    Integer32,
                zxr10OpticalDis9um
                    Integer32,
                zxr10OpticalDis50um 
                    Integer32,
                zxr10OpticalDis62um 
                    Integer32,                  
                zxr10OpticalDiscopperLine
                    Integer32,
                zxr10OpticalSWaveLenth
                    DisplayString,
                zxr10OpticalSWaveLenthValid
                    Integer32,
                zxr10OpticalSRxPower
                    DisplayString,
                zxr10OpticalSRxPowerValid
                    Integer32,
                zxr10OpticalSTxPower
                    DisplayString,
                zxr10OpticalSTxPowerValid
                    Integer32,
                zxr10OpticalSTxCurrent
                    DisplayString,
                zxr10OpticalSTxCurrentValid
                    Integer32,
                zxr10OpticalSTemperature
                    DisplayString,
                zxr10OpticalSTemperatureValid
                    Integer32,
                zxr10Optical33SVoltage
                    DisplayString,
                zxr10Optical33SVoltageValid
                    Integer32,
                zxr10Optical5SVoltage
                    DisplayString,
                zxr10Optical5SVoltageValid
                    Integer32,
                zxr10OpticalVName 
                    DisplayString,
                zxr10OpticalVPn 
                    DisplayString,
                zxr10OpticalRev 
                    DisplayString,
                zxr10OpticalVSn 
                    DisplayString,
                zxr10OpticalSRxPowerChannel1
                    DisplayString,
                zxr10OpticalSRxPowerChannel1Valid
                    Integer32,
                zxr10OpticalSRxPowerChannel2
                    DisplayString,
                zxr10OpticalSRxPowerChannel2Valid
                    Integer32, 
                zxr10OpticalSRxPowerChannel3
                    DisplayString,
                zxr10OpticalSRxPowerChannel3Valid
                    Integer32, 
                zxr10OpticalSRxPowerChannel4
                    DisplayString,
                zxr10OpticalSRxPowerChannel4Valid
                    Integer32, 
                zxr10OpticalSTxPowerChannel1
                    DisplayString,
                zxr10OpticalSTxPowerChannel1Valid
                    Integer32,
                zxr10OpticalSTxPowerChannel2
                    DisplayString,
                zxr10OpticalSTxPowerChannel2Valid
                    Integer32,
                zxr10OpticalSTxPowerChannel3
                    DisplayString,
                zxr10OpticalSTxPowerChannel3Valid
                    Integer32,
                zxr10OpticalSTxPowerChannel4
                    DisplayString,
                zxr10OpticalSTxPowerChannel4Valid
                    Integer32,
                zxr10OpticalSTxCurrentChannel1
                    DisplayString,
                zxr10OpticalSTxCurrentChannel1Valid
                    Integer32,
                zxr10OpticalSTxCurrentChannel2
                    DisplayString,
                zxr10OpticalSTxCurrentChannel2Valid
                    Integer32,
                zxr10OpticalSTxCurrentChannel3
                    DisplayString,
                zxr10OpticalSTxCurrentChannel3Valid
                    Integer32,
                zxr10OpticalSTxCurrentChannel4
                    DisplayString,
                zxr10OpticalSTxCurrentChannel4Valid
                    Integer32,
                zxr10OpticalSTemperatureChannel1
                    DisplayString,
                zxr10OpticalSTemperatureChannel1Valid
                    Integer32, 
                zxr10OpticalSTemperatureChannel2
                    DisplayString,
                zxr10OpticalSTemperatureChannel2Valid
                    Integer32, 
                zxr10OpticalSTemperatureChannel3
                    DisplayString,
                zxr10OpticalSTemperatureChannel3Valid
                    Integer32,
                zxr10OpticalSTemperatureChannel4
                    DisplayString,
                zxr10OpticalSTemperatureChannel4Valid
                    Integer32
              }

    zxr10OpticalIfIndex  OBJECT-TYPE
        SYNTAX  Integer32 
        MAX-ACCESS  read-only 
        STATUS  current
        DESCRIPTION
            "Physical Ethnet interface ifIndex"
        ::= { zxr10OpticalEntry 1 }  
          
    zxr10OpticalIfName  OBJECT-TYPE
        SYNTAX  DisplayString(SIZE(0..32))
        MAX-ACCESS  read-only 
        STATUS  current
        DESCRIPTION
            "Physical Ethnet interface ifName"
        ::= { zxr10OpticalEntry 2 } 
    zxr10OpticalOnline  OBJECT-TYPE
        SYNTAX  OpticalOnline 
        MAX-ACCESS  read-only 
        STATUS  current
        DESCRIPTION
            "Optical Module is Online"
        ::= { zxr10OpticalEntry 3 } 
        
    zxr10OpticalFpType  OBJECT-TYPE
        SYNTAX  DisplayString(SIZE(0..32)) 
        MAX-ACCESS  read-only 
        STATUS  current
        DESCRIPTION
            "Optical Module Info FpType"
        ::= { zxr10OpticalEntry 4 }                        
                                  
    zxr10OpticalSonetComplianceCodesType  OBJECT-TYPE
        SYNTAX  SonetComplianceCodesType 
        MAX-ACCESS  read-only 
        STATUS  current
        DESCRIPTION
            "Sonet Compliance Codes Type"
        ::= { zxr10OpticalEntry 5 } 
                
     zxr10OpticalSonetComplianceCodesSpeed  OBJECT-TYPE
        SYNTAX  SonetComplianceCodesSpeed 
        MAX-ACCESS  read-only 
        STATUS  current
        DESCRIPTION
            "Sonet Compliance Codes Speed"
        ::= { zxr10OpticalEntry 6 } 
    
    zxr10OpticalGigabitEthernetComplianceCodesType  OBJECT-TYPE
        SYNTAX  DisplayString 
        MAX-ACCESS  read-only 
        STATUS  current
        DESCRIPTION
            "Gigabit Ethernet Compliance Codes Type"
        ::= { zxr10OpticalEntry 7 } 
                
     zxr10OpticalGigabitEthernetComplianceCodesSpeed  OBJECT-TYPE
        SYNTAX  GigabitEthernetComplianceCodesSpeed 
        MAX-ACCESS  read-only 
        STATUS  current
        DESCRIPTION
            "Gigabit Ethernet Compliance Codes Speed"
        ::= { zxr10OpticalEntry 8 } 
     
     zxr10OpticalInfinibandComplianceCodesType  OBJECT-TYPE
        SYNTAX  InfinibandComplianceCodesType 
        MAX-ACCESS  read-only 
        STATUS  current
        DESCRIPTION
            "Infiniband Compliance Codes Type"
        ::= { zxr10OpticalEntry 9 } 
                
     zxr10OpticalInfinibandComplianceCodesSpeed  OBJECT-TYPE
        SYNTAX  InfinibandComplianceCodesSpeed 
        MAX-ACCESS  read-only 
        STATUS  current
        DESCRIPTION
            "Infiniband Compliance Codes Speed"
        ::= { zxr10OpticalEntry 10 }               
                      
    zxr10OpticalDisSMFkm  OBJECT-TYPE
        SYNTAX  Integer32 
        MAX-ACCESS  read-only 
        STATUS  current
        DESCRIPTION
            "Optical Module Info DisSMFkm"
        ::= { zxr10OpticalEntry 11 } 
     
     zxr10OpticalDis9um  OBJECT-TYPE
        SYNTAX  Integer32 
        MAX-ACCESS  read-only 
        STATUS  current
        DESCRIPTION
            "Optical Module Info Dis9-125um"
        ::= { zxr10OpticalEntry 12 } 
        
    zxr10OpticalDis50um  OBJECT-TYPE
        SYNTAX  Integer32 
        MAX-ACCESS  read-only 
        STATUS  current
        DESCRIPTION
            "Optical Module Info Dis50-125um"
        ::= { zxr10OpticalEntry 13 } 
        
    zxr10OpticalDis62um  OBJECT-TYPE
        SYNTAX  Integer32 
        MAX-ACCESS  read-only 
        STATUS  current
        DESCRIPTION
            "Optical Module Info Dis62-125um"
        ::= { zxr10OpticalEntry 14 } 
        
    zxr10OpticalDiscopperLine  OBJECT-TYPE
        SYNTAX  Integer32 
        MAX-ACCESS  read-only 
        STATUS  current
        DESCRIPTION
            "Optical Module Info DiscopperLine"
        ::= { zxr10OpticalEntry 15 } 
        
    zxr10OpticalSWaveLenth  OBJECT-TYPE
        SYNTAX  DisplayString 
        MAX-ACCESS  read-only 
        STATUS  current
        DESCRIPTION
            "Optical Module Info S-waveLenth"
        ::= { zxr10OpticalEntry 16 } 
        
    zxr10OpticalSWaveLenthValid  OBJECT-TYPE
        SYNTAX  Integer32 
        MAX-ACCESS  read-only 
        STATUS  current
        DESCRIPTION
            "Optical Module Info S-waveLenthValid"
        ::= { zxr10OpticalEntry 17 } 
   
    zxr10OpticalSRxPower  OBJECT-TYPE
        SYNTAX  DisplayString(SIZE(0..32)) 
        MAX-ACCESS  read-only 
        STATUS  current
        DESCRIPTION
            "Optical Module Info S-rxPower"
        ::= { zxr10OpticalEntry 18 } 
        
    zxr10OpticalSRxPowerValid  OBJECT-TYPE
        SYNTAX  Integer32 
        MAX-ACCESS  read-only 
        STATUS  current
        DESCRIPTION
            "Optical Module Info S-rxPowerValid"
        ::= { zxr10OpticalEntry 19 } 
        
    zxr10OpticalSTxPower  OBJECT-TYPE
        SYNTAX  DisplayString(SIZE(0..32)) 
        MAX-ACCESS  read-only 
        STATUS  current
        DESCRIPTION
            "Optical Module Info S-txPower"
        ::= { zxr10OpticalEntry 20 } 
        
    zxr10OpticalSTxPowerValid  OBJECT-TYPE
        SYNTAX  Integer32 
        MAX-ACCESS  read-only 
        STATUS  current
        DESCRIPTION
            "Optical Module Info S-txPowerValid"
        ::= { zxr10OpticalEntry 21 } 
      
    zxr10OpticalSTxCurrent  OBJECT-TYPE
        SYNTAX  DisplayString(SIZE(0..32)) 
        MAX-ACCESS  read-only 
        STATUS  current
        DESCRIPTION
            "Optical Module Info S-txCurren"
        ::= { zxr10OpticalEntry 22 } 
        
    zxr10OpticalSTxCurrentValid  OBJECT-TYPE
        SYNTAX  Integer32 
        MAX-ACCESS  read-only 
        STATUS  current
        DESCRIPTION
            "Optical Module Info S-txCurrentValid"
        ::= { zxr10OpticalEntry 23 } 
        
    zxr10OpticalSTemperature  OBJECT-TYPE
        SYNTAX  DisplayString(SIZE(0..32)) 
        MAX-ACCESS  read-only 
        STATUS  current
        DESCRIPTION
            "Optical Module Info S-temperature"
        ::= { zxr10OpticalEntry 24 } 
        
    zxr10OpticalSTemperatureValid  OBJECT-TYPE
        SYNTAX  Integer32 
        MAX-ACCESS  read-only 
        STATUS  current
        DESCRIPTION
            "Optical Module Info S-temperatureValid"
        ::= { zxr10OpticalEntry 25 } 
        
    zxr10Optical33SVoltage  OBJECT-TYPE
        SYNTAX  DisplayString(SIZE(0..32)) 
        MAX-ACCESS  read-only 
        STATUS  current
        DESCRIPTION
            "Optical Module Info 3.3 S-voltage"
        ::= { zxr10OpticalEntry 26 } 
        
    zxr10Optical33SVoltageValid  OBJECT-TYPE
        SYNTAX  Integer32 
        MAX-ACCESS  read-only 
        STATUS  current
        DESCRIPTION
            "Optical Module Info 3.3 S-voltageValid"
        ::= { zxr10OpticalEntry 27 } 
    
    zxr10Optical5SVoltage  OBJECT-TYPE
        SYNTAX  DisplayString(SIZE(0..32)) 
        MAX-ACCESS  read-only 
        STATUS  current
        DESCRIPTION
            "Optical Module Info 5 S-voltage"
        ::= { zxr10OpticalEntry 28 } 
        
    zxr10Optical5SVoltageValid  OBJECT-TYPE
        SYNTAX  Integer32 
        MAX-ACCESS  read-only 
        STATUS  current
        DESCRIPTION
            "Optical Module Info 5 S-voltageValid"
        ::= { zxr10OpticalEntry 29 } 
        
    zxr10OpticalVName  OBJECT-TYPE
        SYNTAX  DisplayString(SIZE(0..32)) 
        MAX-ACCESS  read-only 
        STATUS  current
        DESCRIPTION
            "Optical Module Info VName"
        ::= { zxr10OpticalEntry 30 } 
     
    zxr10OpticalVPn  OBJECT-TYPE
        SYNTAX  DisplayString(SIZE(0..32)) 
        MAX-ACCESS  read-only 
        STATUS  current
        DESCRIPTION
            "Optical Module Info VPn"
        ::= { zxr10OpticalEntry 31 } 
    
    zxr10OpticalRev  OBJECT-TYPE
        SYNTAX  DisplayString(SIZE(0..32)) 
        MAX-ACCESS  read-only 
        STATUS  current
        DESCRIPTION
            "Optical Module Info Rev"
        ::= { zxr10OpticalEntry 32 } 
        
    zxr10OpticalVSn  OBJECT-TYPE
        SYNTAX  DisplayString(SIZE(0..32)) 
        MAX-ACCESS  read-only 
        STATUS  current
        DESCRIPTION
            "Optical Module Info VSn"
        ::= { zxr10OpticalEntry 33 } 
    
    zxr10OpticalSRxPowerChannel1  OBJECT-TYPE
        SYNTAX  DisplayString(SIZE(0..32)) 
        MAX-ACCESS  read-only 
        STATUS  current
        DESCRIPTION
            "Optical Module Info Channel1 S-rxPower"
        ::= { zxr10OpticalEntry 34 } 
        
    zxr10OpticalSRxPowerChannel1Valid  OBJECT-TYPE
        SYNTAX  Integer32 
        MAX-ACCESS  read-only 
        STATUS  current
        DESCRIPTION
            "Optical Module Info Channel1 S-rxPowerValid"
        ::= { zxr10OpticalEntry 35 } 
        
    zxr10OpticalSRxPowerChannel2  OBJECT-TYPE
        SYNTAX  DisplayString(SIZE(0..32)) 
        MAX-ACCESS  read-only 
        STATUS  current
        DESCRIPTION
            "Optical Module Info Channel2 S-rxPower"
        ::= { zxr10OpticalEntry 36 } 
        
    zxr10OpticalSRxPowerChannel2Valid  OBJECT-TYPE
        SYNTAX  Integer32 
        MAX-ACCESS  read-only 
        STATUS  current
        DESCRIPTION
            "Optical Module Info Channel2 S-rxPowerValid"
        ::= { zxr10OpticalEntry 37 }  
    
    zxr10OpticalSRxPowerChannel3  OBJECT-TYPE
        SYNTAX  DisplayString(SIZE(0..32)) 
        MAX-ACCESS  read-only 
        STATUS  current
        DESCRIPTION
            "Optical Module Info Channel3 S-rxPower"
        ::= { zxr10OpticalEntry 38 } 
        
    zxr10OpticalSRxPowerChannel3Valid  OBJECT-TYPE
        SYNTAX  Integer32 
        MAX-ACCESS  read-only 
        STATUS  current
        DESCRIPTION
            "Optical Module Info Channel3 S-rxPowerValid"
        ::= { zxr10OpticalEntry 39 }  
        
    zxr10OpticalSRxPowerChannel4  OBJECT-TYPE
        SYNTAX  DisplayString(SIZE(0..32)) 
        MAX-ACCESS  read-only 
        STATUS  current
        DESCRIPTION
            "Optical Module Info Channel4 S-rxPower"
        ::= { zxr10OpticalEntry 40 } 
        
    zxr10OpticalSRxPowerChannel4Valid  OBJECT-TYPE
        SYNTAX  Integer32 
        MAX-ACCESS  read-only 
        STATUS  current
        DESCRIPTION
            "Optical Module Info Channel4 S-rxPowerValid"
        ::= { zxr10OpticalEntry 41 }

        
    zxr10OpticalSTxPowerChannel1  OBJECT-TYPE
        SYNTAX  DisplayString(SIZE(0..32)) 
        MAX-ACCESS  read-only 
        STATUS  current
        DESCRIPTION
            "Optical Module Info Channel1 S-txPower"
        ::= { zxr10OpticalEntry 42 } 
        
    zxr10OpticalSTxPowerChannel1Valid  OBJECT-TYPE
        SYNTAX  Integer32 
        MAX-ACCESS  read-only 
        STATUS  current
        DESCRIPTION
            "Optical Module Info Channel1 S-txPowerValid"
        ::= { zxr10OpticalEntry 43 } 
        
    zxr10OpticalSTxPowerChannel2  OBJECT-TYPE
        SYNTAX  DisplayString(SIZE(0..32)) 
        MAX-ACCESS  read-only 
        STATUS  current
        DESCRIPTION
            "Optical Module Info Channel2 S-txPower"
        ::= { zxr10OpticalEntry 44 } 
        
    zxr10OpticalSTxPowerChannel2Valid  OBJECT-TYPE
        SYNTAX  Integer32 
        MAX-ACCESS  read-only 
        STATUS  current
        DESCRIPTION
            "Optical Module Info Channel2 S-txPowerValid"
        ::= { zxr10OpticalEntry 45 }  
        
    zxr10OpticalSTxPowerChannel3  OBJECT-TYPE
        SYNTAX  DisplayString(SIZE(0..32)) 
        MAX-ACCESS  read-only 
        STATUS  current
        DESCRIPTION
            "Optical Module Info Channel3 S-txPower"
        ::= { zxr10OpticalEntry 46 } 
        
    zxr10OpticalSTxPowerChannel3Valid  OBJECT-TYPE
        SYNTAX  Integer32 
        MAX-ACCESS  read-only 
        STATUS  current
        DESCRIPTION
            "Optical Module Info Channel3 S-txPowerValid"
        ::= { zxr10OpticalEntry 47 }
        
    zxr10OpticalSTxPowerChannel4  OBJECT-TYPE
        SYNTAX  DisplayString(SIZE(0..32)) 
        MAX-ACCESS  read-only 
        STATUS  current
        DESCRIPTION
            "Optical Module Info Channel4 S-txPower"
        ::= { zxr10OpticalEntry 48 } 
        
    zxr10OpticalSTxPowerChannel4Valid  OBJECT-TYPE
        SYNTAX  Integer32 
        MAX-ACCESS  read-only 
        STATUS  current
        DESCRIPTION
            "Optical Module Info Channel4 S-txPowerValid"
        ::= { zxr10OpticalEntry 49 }

      
    zxr10OpticalSTxCurrentChannel1  OBJECT-TYPE
        SYNTAX  DisplayString(SIZE(0..32)) 
        MAX-ACCESS  read-only 
        STATUS  current
        DESCRIPTION
            "Optical Module Info Channel1 S-txCurren"
        ::= { zxr10OpticalEntry 50 } 
        
    zxr10OpticalSTxCurrentChannel1Valid  OBJECT-TYPE
        SYNTAX  Integer32 
        MAX-ACCESS  read-only 
        STATUS  current
        DESCRIPTION
            "Optical Module Info Channel1 S-txCurrentValid"
        ::= { zxr10OpticalEntry 51 } 
        
    zxr10OpticalSTxCurrentChannel2  OBJECT-TYPE
        SYNTAX  DisplayString(SIZE(0..32)) 
        MAX-ACCESS  read-only 
        STATUS  current
        DESCRIPTION
            "Optical Module Info Channel2 S-txCurren"
        ::= { zxr10OpticalEntry 52 } 
        
    zxr10OpticalSTxCurrentChannel2Valid  OBJECT-TYPE
        SYNTAX  Integer32 
        MAX-ACCESS  read-only 
        STATUS  current
        DESCRIPTION
            "Optical Module Info Channel2 S-txCurrentValid"
        ::= { zxr10OpticalEntry 53 } 
        
    zxr10OpticalSTxCurrentChannel3  OBJECT-TYPE
        SYNTAX  DisplayString(SIZE(0..32)) 
        MAX-ACCESS  read-only 
        STATUS  current
        DESCRIPTION
            "Optical Module Info Channel3 S-txCurren"
        ::= { zxr10OpticalEntry 54 } 
        
    zxr10OpticalSTxCurrentChannel3Valid  OBJECT-TYPE
        SYNTAX  Integer32 
        MAX-ACCESS  read-only 
        STATUS  current
        DESCRIPTION
            "Optical Module Info Channel3 S-txCurrentValid"
        ::= { zxr10OpticalEntry 55 }  
    
    zxr10OpticalSTxCurrentChannel4  OBJECT-TYPE
        SYNTAX  DisplayString(SIZE(0..32)) 
        MAX-ACCESS  read-only 
        STATUS  current
        DESCRIPTION
            "Optical Module Info Channel4 S-txCurren"
        ::= { zxr10OpticalEntry 56 } 
        
    zxr10OpticalSTxCurrentChannel4Valid  OBJECT-TYPE
        SYNTAX  Integer32 
        MAX-ACCESS  read-only 
        STATUS  current
        DESCRIPTION
            "Optical Module Info Channel4 S-txCurrentValid"
        ::= { zxr10OpticalEntry 57 }
        
    zxr10OpticalSTemperatureChannel1  OBJECT-TYPE
        SYNTAX  DisplayString(SIZE(0..32)) 
        MAX-ACCESS  read-only 
        STATUS  current
        DESCRIPTION
            "Optical Module Info Channel1 S-temperature"
        ::= { zxr10OpticalEntry 58 } 
        
    zxr10OpticalSTemperatureChannel1Valid  OBJECT-TYPE
        SYNTAX  Integer32 
        MAX-ACCESS  read-only 
        STATUS  current
        DESCRIPTION
            "Optical Module Info Channel1 S-temperatureValid"
        ::= { zxr10OpticalEntry 59 }  
    zxr10OpticalSTemperatureChannel2  OBJECT-TYPE
        SYNTAX  DisplayString(SIZE(0..32)) 
        MAX-ACCESS  read-only 
        STATUS  current
        DESCRIPTION
            "Optical Module Info Channel2 S-temperature"
        ::= { zxr10OpticalEntry 60 } 
        
    zxr10OpticalSTemperatureChannel2Valid  OBJECT-TYPE
        SYNTAX  Integer32 
        MAX-ACCESS  read-only 
        STATUS  current
        DESCRIPTION
            "Optical Module Info Channel2 S-temperatureValid"
        ::= { zxr10OpticalEntry 61 } 
    zxr10OpticalSTemperatureChannel3  OBJECT-TYPE
        SYNTAX  DisplayString(SIZE(0..32)) 
        MAX-ACCESS  read-only 
        STATUS  current
        DESCRIPTION
            "Optical Module Info Channel3 S-temperature"
        ::= { zxr10OpticalEntry 62 } 
        
    zxr10OpticalSTemperatureChannel3Valid  OBJECT-TYPE
        SYNTAX  Integer32 
        MAX-ACCESS  read-only 
        STATUS  current
        DESCRIPTION
            "Optical Module Info Channel3 S-temperatureValid"
        ::= { zxr10OpticalEntry 63 } 
        
    zxr10OpticalSTemperatureChannel4  OBJECT-TYPE
        SYNTAX  DisplayString(SIZE(0..32)) 
        MAX-ACCESS  read-only 
        STATUS  current
        DESCRIPTION
            "Optical Module Info Channel4 S-temperature"
        ::= { zxr10OpticalEntry 64 } 
        
    zxr10OpticalSTemperatureChannel4Valid  OBJECT-TYPE
        SYNTAX  Integer32 
        MAX-ACCESS  read-only 
        STATUS  current
        DESCRIPTION
            "Optical Module Info Channel4 S-temperatureValid"
        ::= { zxr10OpticalEntry 65 } 


END
