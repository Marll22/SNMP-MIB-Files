-- ZyXEL Communications Corporation
-- Private Enterprise MIB definition 
  
-- This file describes the ZyXEL Communications Corporation Enterprise MIB.
-- It contains ZyXEL products OIDs, and common managed objects.

-- $Log: ZYXEL-MAC-FILTER-MIB.mib $ 
-- Revision 1.3  2012/09/19 07:40:50  Kevin 
-- if it's leaf node, revise the vender name from zyxel to zy 
-- Revision 1.2  2012/07/05 06:23:36  Kevin 
-- 1. upgrade from SNMP to SNMPv2  
-- 2. clean warning 
-- Revision 1.1  2012/05/30 07:49:47  Kevin 
-- Initial revision 

ZYXEL-MAC-FILTER-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelMacFilter MODULE-IDENTITY
		LAST-UPDATED	"201207010000Z"    
		ORGANIZATION "Enterprise Solution ZyXEL"     
		CONTACT-INFO
			""	   
		DESCRIPTION
			"The subtree for MAC filter"
		::= { esMgmt 47 }
		
	zyxelMacFilterSetup	    OBJECT IDENTIFIER ::= { zyxelMacFilter 1 }
	       		                      
        
        zyMacFilterMaxNumberOfRules OBJECT-TYPE
        SYNTAX  INTEGER
        MAX-ACCESS  read-only
        STATUS  current
        DESCRIPTION
			"The maximum number of filter rule that can be created."
        ::= { zyxelMacFilterSetup 1 }
                                             
--  	zyxelMacFilterTable
       	zyxelMacFilterTable	OBJECT-TYPE
        SYNTAX	SEQUENCE OF ZyxelMacFilterEntry
        MAX-ACCESS  not-accessible
        STATUS  current
        DESCRIPTION
			"The table contains MAC filter configuration."
        ::= { zyxelMacFilterSetup 2 }
        
		zyxelMacFilterEntry OBJECT-TYPE
        SYNTAX	ZyxelMacFilterEntry
        MAX-ACCESS	not-accessible
        STATUS	current
        DESCRIPTION    	
        	"An entry contains MAC filter configuration."
        INDEX          	{ zyMacFilterMacAddress, zyMacFilterVid }
        ::= { zyxelMacFilterTable 1 }

        ZyxelMacFilterEntry ::=
           SEQUENCE {
        	zyMacFilterMacAddress	MacAddress,
        	zyMacFilterVid			INTEGER,           
         	zyMacFilterName			DisplayString,
        	zyMacFilterAction		INTEGER,
        	zyMacFilterRowStatus	RowStatus
           }
       

        zyMacFilterMacAddress OBJECT-TYPE
        SYNTAX  MacAddress
        MAX-ACCESS  not-accessible
        STATUS  current
        DESCRIPTION
			"Type a MAC address in valid MAC address format, that is , six hexadecimal character pairs."
        ::= { zyxelMacFilterEntry 1 }

   		zyMacFilterVid OBJECT-TYPE
        SYNTAX  INTEGER
        MAX-ACCESS  not-accessible
        STATUS  current
        DESCRIPTION
			"The VLAN group identificaton number."
        ::= { zyxelMacFilterEntry 2 }   

        zyMacFilterName OBJECT-TYPE
        SYNTAX  DisplayString
        MAX-ACCESS  read-write
        STATUS  current
        DESCRIPTION
			"A descriptive name for this rule. This is for identification only."
        ::= { zyxelMacFilterEntry 3 }

        zyMacFilterAction OBJECT-TYPE
        SYNTAX  INTEGER {
			discard-source(1),
			discard-destination(2),
			both(3)
		}
        MAX-ACCESS  read-write
        STATUS  current
        DESCRIPTION
			"1.discard source : drop the frames from the source MAC address. 
			 The switch can still send frames to the MAC address. 
			 2. discard destination: drop the frames to the destination MAC address.
			 The switch can still receive frames originating from the MAC address.
			 3. both : block traffic to/from the MAC address specified in the MAC field."
        ::= { zyxelMacFilterEntry 4 }        

   		zyMacFilterRowStatus OBJECT-TYPE
        SYNTAX  RowStatus
        MAX-ACCESS  read-create
        STATUS  current
        DESCRIPTION
			"This object allows entries to be created and deleted from the filter table."
        ::= { zyxelMacFilterEntry 5 }

END
