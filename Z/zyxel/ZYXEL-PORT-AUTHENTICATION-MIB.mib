-- ZyXEL Communications Corporation
-- Private Enterprise MIB definition 
  
-- This file describes the ZyXEL Communications Corporation Enterprise MIB.
-- It contains ZyXEL products OIDs, and common managed objects.

-- $Log: ZYXEL-PORT-AUTHENTICATION-MIB.mib $ 
-- Revision 1.4  2012/09/19 07:43:52  Kevin 
-- if it's leaf node, revise the vender name from zyxel to zy 
-- Revision 1.3  2012/08/22 09:47:30  Kevin 
-- clean warning for SNMPc 
-- Revision 1.2  2012/07/05 06:24:13  Kevin 
-- 1. upgrade from SNMP to SNMPv2  
-- 2. clean warning 
-- Revision 1.1  2012/05/30 07:50:24  Kevin 
-- Initial revision 

ZYXEL-PORT-AUTHENTICATION-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelPortAuthentication MODULE-IDENTITY
		LAST-UPDATED	"201207010000Z"    
		ORGANIZATION "Enterprise Solution ZyXEL"     
		CONTACT-INFO
			""	   
		DESCRIPTION
			"The subtree for port authentication"
		::= { esMgmt 62 }
		
	zyxelPortAuthenticationSetup    OBJECT IDENTIFIER ::= { zyxelPortAuthentication 1 }
	
  
-- *******************************************************************
-- *
-- * zyxelPortAuthenticationSetup
-- *
-- *******************************************************************

-- zyxelPortAuthenticationState
		zyPortAuthenticationState	OBJECT-TYPE
        SYNTAX  EnabledStatus
        MAX-ACCESS  read-write
        STATUS  current
        DESCRIPTION
                      	"Enable/Disable 802.1x port authentication for the switch."
        ::= { zyxelPortAuthenticationSetup 1 }
		
-- zyxelPortAuthenticationTable 
		zyxelPortAuthenticationPortTable	OBJECT-TYPE
        SYNTAX	SEQUENCE OF ZyxelPortAuthenticationPortEntry
        MAX-ACCESS  not-accessible
        STATUS  current
        DESCRIPTION
                 	"The table contains port authentication configuration"
        ::= { zyxelPortAuthenticationSetup 2 }
        
		zyxelPortAuthenticationPortEntry OBJECT-TYPE
        SYNTAX	ZyxelPortAuthenticationPortEntry
        MAX-ACCESS	not-accessible
        STATUS	current
        DESCRIPTION    	
					"An entry contains port authentication configuration."
        INDEX          	{ dot1dBasePort }
        ::= { zyxelPortAuthenticationPortTable 1 }

        ZyxelPortAuthenticationPortEntry ::=
           SEQUENCE {
        	zyPortAuthenticationPortState								EnabledStatus,
        	zyPortReAuthenticationPortState								EnabledStatus,
        	zyPortReAuthenticationPortTimer								INTEGER ,
        	zyPortAuthenticationPortQuietPeriod							INTEGER ,
        	zyPortAuthenticationPortTxPeriod							INTEGER ,
        	zyPortAuthenticationPortSupplicantTimeout					INTEGER ,
        	zyPortAuthenticationPortMaxRequest							INTEGER ,
        	zyPortAuthenticationPortGuestVlanState						EnabledStatus,
        	zyPortAuthenticationPortGuestVlan							INTEGER ,
        	zyPortAuthenticationPortGuestVlanHostMode					INTEGER ,
        	zyPortAuthenticationPortGuestVlanHostModeMultiSecureNumber	INTEGER 
           }

        zyPortAuthenticationPortState OBJECT-TYPE
        SYNTAX  EnabledStatus
        MAX-ACCESS  read-write
        STATUS  current
        DESCRIPTION
			"Enable/Disable 802.1x port authentication on the port. You must first allow 802.1x authentication on 
			the Switch before configuring it on each port. "
        ::= { zyxelPortAuthenticationPortEntry 1 }

        zyPortReAuthenticationPortState OBJECT-TYPE
        SYNTAX  EnabledStatus
        MAX-ACCESS  read-write
        STATUS  current
        DESCRIPTION
			"Enable/Disable 802.1x port re-authentication on the port. Specify if a subscriber has to periodically 
			re-enter his or her username and password to stay connected to the port."
        ::= { zyxelPortAuthenticationPortEntry 2 }

        zyPortReAuthenticationPortTimer OBJECT-TYPE
        SYNTAX  INTEGER
        MAX-ACCESS  read-write
        STATUS  current
        DESCRIPTION
			"Specify the length of time required to pass before a client has to re-enter his or her username and 
			password to stay connected to the port. "
        ::= { zyxelPortAuthenticationPortEntry 3 }

		zyPortAuthenticationPortQuietPeriod OBJECT-TYPE
        SYNTAX  INTEGER
        MAX-ACCESS  read-write
        STATUS  current
        DESCRIPTION
			"Specify the number of seconds the port remains in the HELD state and rejects further authentication 
			requests from the connected client after a failed authentication exchange. "
        ::= { zyxelPortAuthenticationPortEntry 4 }
        
        zyPortAuthenticationPortTxPeriod OBJECT-TYPE
        SYNTAX  INTEGER
        MAX-ACCESS  read-write
        STATUS  current
        DESCRIPTION
			"Specify the number of seconds the Switch waits for client's response before re-sending an identity 
			request to the client.  "
        ::= { zyxelPortAuthenticationPortEntry 5 }   
        
        zyPortAuthenticationPortSupplicantTimeout OBJECT-TYPE
        SYNTAX  INTEGER
        MAX-ACCESS  read-write
        STATUS  current
        DESCRIPTION
			"Specify the number of seconds the Switch waits for client's response to a challenge request before 
			sending another request. "
        ::= { zyxelPortAuthenticationPortEntry 6 } 
        
        zyPortAuthenticationPortMaxRequest OBJECT-TYPE
        SYNTAX  INTEGER
        MAX-ACCESS  read-write
        STATUS  current
        DESCRIPTION
			"Specify the number of times the Switch tries to authenticate client(s) before sending unresponsive 
			ports to the Guest VLAN. This is set to 2 by default. That is, the Switch attempts to authenticate a 
			client twice. If the client does not respond to the first authentication request, the Switch tries again. If the client still does not respond to the second request, the Switch sends the client to the Guest VLAN. The client needs to send a new request to be authenticated by the Switch again. "
        ::= { zyxelPortAuthenticationPortEntry 7 }

        zyPortAuthenticationPortGuestVlanState OBJECT-TYPE
        SYNTAX  EnabledStatus
        MAX-ACCESS  read-write
        STATUS  current
        DESCRIPTION
			"Enable/Disable Guest VLAN on the port. Clients that fail authentication are placed in the guest VLAN 
			and can receive limited services. "
        ::= { zyxelPortAuthenticationPortEntry 8 }
                                 
        zyPortAuthenticationPortGuestVlan OBJECT-TYPE
        SYNTAX  INTEGER
        MAX-ACCESS  read-write
        STATUS  current
        DESCRIPTION
			"Enter the number that identifies the guest VLAN. Make sure this is a VLAN recognized in your network. 
			A guest VLAN is a pre-configured VLAN on the Switch that allows non-authenticated users to access 
			limited network resources through the Switch. You must also enable IEEE 802.1x authentication on the 
			Switch and the associated ports. "
        ::= { zyxelPortAuthenticationPortEntry 9 }

        zyPortAuthenticationPortGuestVlanHostMode OBJECT-TYPE
        SYNTAX  INTEGER	{
             multi-Host(0),
             multi-Secure(1)
        	}
        MAX-ACCESS  read-write
        STATUS  current
        DESCRIPTION
			"Specify how the Switch authenticates users when more than one user connect to the port (using a hub). 
			Select Multi-Host to authenticate only the first user that connects to this port. If the first user 
			enters the correct credential, any other users are allowed to access the port without authentication. 
			If the first user fails to enter the correct credential, they are all put in the guest VLAN. Once the 
			first user who did authentication logs out or disconnects from the port, rest of the users are blocked 
			until a user does the authentication process again. 
			Select Multi-Secure to authenticate each user that connects to this port. "
        ::= { zyxelPortAuthenticationPortEntry 10 }   
        
        zyPortAuthenticationPortGuestVlanHostModeMultiSecureNumber OBJECT-TYPE
        SYNTAX  INTEGER
        MAX-ACCESS  read-write
        STATUS  current
        DESCRIPTION
			"If you set Host-mode to Multi-Secure, specify the maximum number of users that the 
			Switch will authenticate on this port. "
        ::= { zyxelPortAuthenticationPortEntry 11 }

END
