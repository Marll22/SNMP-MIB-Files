-- **********************************************
-- ZyXEL Communications Corporation
--
-- Enterprise Solution MIB definitions
-- Hybrid AP MIBs 
--
-- LiKuang Tsai
--
-- Copyright by ZyXEL Communications Corp.
-- All rights reserved.
-- **********************************************

ZYXEL-ES-HybridAP DEFINITIONS ::= BEGIN

IMPORTS

	MODULE-IDENTITY,
	OBJECT-IDENTITY,
	OBJECT-TYPE		FROM SNMPv2-SMI

	OBJECT-GROUP,
	MODULE-COMPLIANCE	FROM SNMPv2-CONF

	esMgmt			FROM ZYXEL-ES-SMI;

esHybridAP MODULE-IDENTITY
	LAST-UPDATED	"201010060000Z"    
	ORGANIZATION "Enterprise Solution ZyXEL"     
	CONTACT-INFO
		""	   
	DESCRIPTION
		"The subtree for esHybridAP information"
	::= { esMgmt 4 }


-- esHybridAP OIDs
                                    
	
	operationMode OBJECT-TYPE
		SYNTAX	  INTEGER  {
			standalone (1),
    		controller (2),
    		managed (3),
    		max (4)
		}
		MAX-ACCESS  read-only
		STATUS  current
		DESCRIPTION
			"Hybrid Mode"
	::= { esHybridAP 1 } 	
                                 	                           
END
