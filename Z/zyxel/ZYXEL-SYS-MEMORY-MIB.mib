-- ZyXEL Communications Corporation
-- Private Enterprise MIB definition 
  
-- This file describes the ZyXEL Communications Corporation Enterprise MIB.
-- It contains ZyXEL products OIDs, and common managed objects.

-- $Log: ZYXEL-SYS-MEMORY-MIB.mib $ 
-- Revision 1.3  2012/09/19 07:47:18  Kevin 
-- if it's leaf node, revise the vender name from zyxel to zy 
-- Revision 1.2  2012/07/05 06:24:46  Kevin 
-- 1. upgrade from SNMP to SNMPv2  
-- 2. clean warning 
-- Revision 1.1  2012/05/30 07:50:49  Kevin 
-- Initial revision 

ZYXEL-SYS-MEMORY-MIB DEFINITIONS ::= BEGIN

    IMPORTS
	enterprises		FROM RFC1155-SMI                                
	
	OBJECT-TYPE, Unsigned32
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelSysMemory MODULE-IDENTITY
		LAST-UPDATED	"201207010000Z"    
		ORGANIZATION "Enterprise Solution ZyXEL"     
		CONTACT-INFO
			""	   
		DESCRIPTION
			"The subtree for system memory"
		::= { esMgmt 50 }	

	zyxelSysMemoryPoolStatus	OBJECT IDENTIFIER ::= { zyxelSysMemory 1 }
                      
        
		zyxelSysMemoryPoolTable OBJECT-TYPE
	    SYNTAX      SEQUENCE OF ZyxelSysMemoryPoolEntry
	    MAX-ACCESS  not-accessible
	    STATUS      current
	    DESCRIPTION
	    	"The table that show memory utilization statistics on the switch."              
    	::= { zyxelSysMemoryPoolStatus 1 } 
    	    
    	zyxelSysMemoryPoolEntry OBJECT-TYPE
        SYNTAX      ZyxelSysMemoryPoolEntry
        MAX-ACCESS  not-accessible
        STATUS      current
        DESCRIPTION
            "Memory utilization statistics information for the switch."
        INDEX {zySysMemoryPoolId }
    	::= { zyxelSysMemoryPoolTable 1 }
    
    	ZyxelSysMemoryPoolEntry ::=
        SEQUENCE {
            zySysMemoryPoolId       		Unsigned32, 
            zySysMemoryPoolName     		OCTET STRING,
            zySysMemoryPoolTotalSize  		Unsigned32, 
            zySysMemoryPoolUsedSize   		Unsigned32,
            zySysMemoryPoolUtilization    	Unsigned32
        } 
    
    	zySysMemoryPoolId OBJECT-TYPE
        SYNTAX      Unsigned32
        MAX-ACCESS  not-accessible
        STATUS      current
        DESCRIPTION
        	"ID of the memory pool."
    	::= { zyxelSysMemoryPoolEntry 1 }
    
    	zySysMemoryPoolName OBJECT-TYPE
        SYNTAX      OCTET STRING(SIZE (0..32))
        MAX-ACCESS  read-only
        STATUS      current
        DESCRIPTION
        	"Name of the memory pool."
    	::= { zyxelSysMemoryPoolEntry 2 }
        
    	zySysMemoryPoolTotalSize OBJECT-TYPE
        SYNTAX      Unsigned32
        MAX-ACCESS  read-only
        STATUS      current
        DESCRIPTION
        	"Total size of memory pool in bytes."
    	::= { zyxelSysMemoryPoolEntry 3 }
    
   		zySysMemoryPoolUsedSize OBJECT-TYPE
        SYNTAX      Unsigned32
        MAX-ACCESS  read-only
        STATUS      current
        DESCRIPTION
        	"Used size of memory pool in bytes."
    	::= { zyxelSysMemoryPoolEntry 4 }
    
    	zySysMemoryPoolUtilization OBJECT-TYPE
        SYNTAX      Unsigned32 (0..100)
        MAX-ACCESS  read-only
        STATUS      current
        DESCRIPTION
        	"Utilization of memory pool in bytes."
    	::= { zyxelSysMemoryPoolEntry 5 }

END
