-- EOC350 private MIB's definitions in ASN.1 format
-- 08-14-2012
      
   ZYXEL-ES-EOC350 DEFINITIONS ::= BEGIN
   
   IMPORTS
       MODULE-IDENTITY, OBJECT-TYPE, NOTIFICATION-TYPE,
       -- mib-2,
       TimeTicks,
       Counter32,
       Counter64,
       -- UInteger32, 
       Integer32,
       IpAddress,
       enterprises
           FROM SNMPv2-SMI
           
       TEXTUAL-CONVENTION, 
       MacAddress, 
       DisplayString,
       -- TimeStamp, 
       -- TruthValue,
       RowStatus 
           FROM SNMPv2-TC
           
       esPartnerProducts
           FROM ZYXEL-ES-SMI    
       ;

       eoc350BrMib          OBJECT IDENTIFIER ::= { esPartnerProducts 1 } -- EoC Master+EP bridge
       eoc350BrNotification OBJECT IDENTIFIER ::= { esPartnerProducts 3 }
    
-- ============================================================================       
-- managed EoC bridge configure mib id 
--      
       eocBrSystemGroup     OBJECT IDENTIFIER ::= { eoc350BrMib 1  }
       eocBrIPGroup         OBJECT IDENTIFIER ::= { eoc350BrMib 2  }
                                                                
--     eocBrGroupObsolete1  OBJECT IDENTIFIER ::= { eoc350BrMib 3  }
                                                                
       eocBrAdminGroup      OBJECT IDENTIFIER ::= { eoc350BrMib 4  }
       eocBrServiceGroup    OBJECT IDENTIFIER ::= { eoc350BrMib 5  }
                                                                
--     eocBrGroupObsolete2  OBJECT IDENTIFIER ::= { eoc350BrMib 6  }
                                                                
       eocBrTFTPGroup       OBJECT IDENTIFIER ::= { eoc350BrMib 9  }
                                                                
       eocBrMasterEoCGroup  OBJECT IDENTIFIER ::= { eoc350BrMib 7  }       
       eocBrEPEoCGroup      OBJECT IDENTIFIER ::= { eoc350BrMib 8  }
       eocBrEtherGroup      OBJECT IDENTIFIER ::= { eoc350BrMib 10 }
       
-- for Smart EP only, EP that is configurable       
       eocBrEPEtherGroup   OBJECT IDENTIFIER  ::= { eoc350BrMib 11 }
     
-- ============================================================================
-- eocBrSystemGroup OBJECT IDENTIFIER ::= { eoc350BrMib 1 }

-- 1,3,6,1,4,1,890,1,15,5,1,1,1
eocBrModel OBJECT-TYPE
       SYNTAX INTEGER { 
--
-- MDU
--
                eOC350-TS    ('9076'h),
                eOC350-TS    ('9075'h),
                eOC350-TS    ('9876'h),
                eOC350-TS    ('9875'h)
       }
       MAX-ACCESS read-only
       STATUS current
       DESCRIPTION
               "Identify the bridge model. "
       ::= { eocBrSystemGroup 1 }
       
-- 1,3,6,1,4,1,890,1,15,5,1,1,2
eocBrProductName OBJECT-TYPE
       SYNTAX DisplayString (SIZE(0..32))
       MAX-ACCESS read-only
       STATUS current
       DESCRIPTION
               "The bridge product name. "
       ::= { eocBrSystemGroup 2 } 

-- 1,3,6,1,4,1,890,1,15,5,1,1,3
eocBrSystemMac OBJECT-TYPE
       SYNTAX MacAddress
       MAX-ACCESS read-only
       STATUS current
       DESCRIPTION
               "The 6-byte Ethernet Mac address of the bridge.  "
       ::= { eocBrSystemGroup 3 }

-- 1,3,6,1,4,1,890,1,15,5,1,1,4
eocBrEoCMac OBJECT-TYPE
       SYNTAX MacAddress
       MAX-ACCESS read-only
       STATUS current
       DESCRIPTION
               "The 6-byte EoC Mac address of the bridge self EoC Master. "
       ::= { eocBrSystemGroup 4}
       
-- 1,3,6,1,4,1,890,1,15,5,1,1,5       
eocBrHardwareVersion OBJECT-TYPE
       SYNTAX DisplayString (SIZE(0..5))
       MAX-ACCESS read-only
       STATUS current
       DESCRIPTION
               "The bridge hardware version. "
       ::= { eocBrSystemGroup 5}
       
-- 1,3,6,1,4,1,890,1,15,5,1,1,6
eocBrBootVersion OBJECT-TYPE
       SYNTAX DisplayString (SIZE(0..16))
       MAX-ACCESS read-only
       STATUS current
       DESCRIPTION
               "The bridge boot loader version. "
       ::= { eocBrSystemGroup 6}
       
-- 1,3,6,1,4,1,890,1,15,5,1,1,7
eocBrSystemFwWorkingVersion OBJECT-TYPE
       SYNTAX DisplayString (SIZE(0..16))
       MAX-ACCESS read-only
       STATUS current
       DESCRIPTION
               "The bridge current working/running system firmware version. "
       ::= { eocBrSystemGroup 7 }
       
-- 1,3,6,1,4,1,890,1,15,5,1,1,8
eocBrSystemFwUploadVersion OBJECT-TYPE
       SYNTAX DisplayString (SIZE(0..16))
       MAX-ACCESS read-only
       STATUS current
       DESCRIPTION
               "The stored system firmware version intended for upgrading
                the bridge. The firmware is placed in the bridge 'upload'
                area temporarily and is uploaded by TFTP or HTTP first. "
       ::= { eocBrSystemGroup 8 }                   
                    
-- 1,3,6,1,4,1,890,1,15,5,1,1,9
eocBrSystemFwUpgradeAction OBJECT-TYPE
       SYNTAX INTEGER {
            idle(0), 
            activateThenReboot(1)
       }
       MAX-ACCESS read-write
       STATUS current
       DESCRIPTION
               "To trigger upgrade operation of the bridge to replace 
                the current firmware (version eocBrSystemFwWorkingVersion) with
                the new uploaded firmware (version eocBrSystemFwUploadVersion). 
                The SNMP manager can upgrade the system firmware by set the 
                value to activate(1); and submit to the bridge to start 
                the upgrade procedure. The status (eocBrSystemFwUpgradeStatus) 
                will go from inProgress(1) status back to the 
                initial normalOrComplete(0) status. "
       ::= { eocBrSystemGroup 9 }
       
-- 1,3,6,1,4,1,890,1,15,5,1,1,10
eocBrSystemFwUpgradeStatus OBJECT-TYPE
       SYNTAX INTEGER {
            normalOrComplete(0), 
            inProgress(1),
            failed(2)
       }
       MAX-ACCESS read-only
       STATUS current
       DESCRIPTION
               "Status for upgrade operation of the bridge to replace 
                the current firmware (version eocBrSystemFwWorkingVersion) with
                the new uploaded firmware (version eocBrSystemFwUploadVersion). 
                The SNMP manager can upgrade the system firmware by set the 
                eocBrSystemFwUpgradeAction value to activate(1); 
                and submit to the bridge to start the upgrade procedure. 
                The status (eocBrSystemFwUpgradeStatus) will go from 
                inProgress(1) status back to the initial 
                normalOrComplete(0) status. "
       ::= { eocBrSystemGroup 10 }
              
-- 1,3,6,1,4,1,890,1,15,5,1,1,11
eocBrSystemReboot OBJECT-TYPE
       SYNTAX INTEGER {
            idle(0), 
            activateThenReboot(1)
       }
       MAX-ACCESS read-write
       STATUS current
       DESCRIPTION
               "Activate to reboot the bridge. "
       ::= { eocBrSystemGroup 11 }
       
-- 1,3,6,1,4,1,890,1,15,5,1,1,15
eocBrAutoEPDrvUpgrade OBJECT-TYPE
       SYNTAX INTEGER {
            disable(0),
            enable(1)
       }
       MAX-ACCESS read-write
       STATUS current
       DESCRIPTION
               "Sync/Upgrade connected EoC EP driver from current 'working/running' version 
                to new 'upload' version automatically. "
       ::= { eocBrSystemGroup 15 }           
                     
-- ============================================================================
-- eocBrIPGroup OBJECT IDENTIFIER ::= { eoc350BrMib 2 }
      
-- 1,3,6,1,4,1,890,1,15,5,1,2,1
eocBrIPAddress OBJECT-TYPE
       SYNTAX IpAddress
       MAX-ACCESS read-write
       STATUS current
       DESCRIPTION
               "IP address of the bridge. "
       ::= { eocBrIPGroup 1 }

-- 1,3,6,1,4,1,890,1,15,5,1,2,2
eocBrSubnetMask OBJECT-TYPE
       SYNTAX IpAddress
       MAX-ACCESS read-write
       STATUS current
       DESCRIPTION
               "Subnet mask of the bridge. "
       ::= { eocBrIPGroup 2 }


-- 1,3,6,1,4,1,890,1,15,5,1,2,3
eocBrDefaultGatewayIPAddress OBJECT-TYPE
       SYNTAX IpAddress
       MAX-ACCESS read-write
       STATUS current
       DESCRIPTION
               "Default gateway for the bridge. "
       ::= { eocBrIPGroup 3 }
       
-- 1,3,6,1,4,1,890,1,15,5,1,2,4
eocBrPrimaryDnsIPAddress OBJECT-TYPE
       SYNTAX IpAddress
       MAX-ACCESS read-write
       STATUS current
       DESCRIPTION
               "Primary DNS for the bridge. "
       ::= { eocBrIPGroup 4 }       

-- 1,3,6,1,4,1,890,1,15,5,1,2,5
eocBrSecondaryDnsIPAddress OBJECT-TYPE
       SYNTAX IpAddress
       MAX-ACCESS read-write
       STATUS current
       DESCRIPTION
               "Secondary DNS for the bridge. "
       ::= { eocBrIPGroup 5}
       
-- 1,3,6,1,4,1,890,1,15,5,1,2,6
eocBrIPAddressAssign OBJECT-TYPE
       SYNTAX INTEGER {
               static(0),
               dynamic-dhcp(1)             
       }
       MAX-ACCESS read-write
       STATUS current
       DESCRIPTION
               "Method to assign the IP address for the bridge. Use the static IP or 
                obtain the dynamic IP from DHCP server by adopting DHCP client. "
       ::= { eocBrIPGroup 6}
       
-- 1,3,6,1,4,1,890,1,15,5,1,2,8
eocBrDHCPLease OBJECT-TYPE
       SYNTAX Integer32
       MAX-ACCESS read-only
       STATUS current
       DESCRIPTION
               "The DHCP IP leased period if the bridge adopt the DHCP client (dynamic-dhcp)
                to get the IP address. Void if bridge is assigned with static IP." 
       ::= { eocBrIPGroup 8} 
 
             
-- 1,3,6,1,4,1,890,1,15,5,1,2,10
eocBrHostDHCPPadOpt82EnableCtrl OBJECT-TYPE
       SYNTAX INTEGER {
               disable(0),
               enable(1)             
       }
       MAX-ACCESS read-write
       STATUS current
       DESCRIPTION
               "Pad the DHCP relay agent information or not. While enabled, bridge will pad DHCP packets 
                sourced from hosts behind EP with option 82 information (Circuit ID and Remote ID).
                DHCP server could use the record of (assigned IP, Circuit ID, Remote ID)
                for IP address assignment management and usage tracking. Circuit ID is the bridge 
                Ethernet Mac address and Remote ID is the EP device Mac address. "
       ::= { eocBrIPGroup 10}
       
-- 1,3,6,1,4,1,890,1,15,5,1,2,12
eocBrHostIPSourceGuardCtrl OBJECT-TYPE
       SYNTAX INTEGER {
               disable(0),
               enable(1)             
       }
       MAX-ACCESS read-write
       STATUS current
       DESCRIPTION
               "Enable the IP Source Guard or not. While enabled, bridge will snoop the DHCP 
                traffic passed to/from host and allow only host with IP/Mac via DHCP could access
                the network. "
       ::= { eocBrIPGroup 12}

-- ----------------------------------------------------------------------------     
-- 1,3,6,1,4,1,890,1,15,5,1,2,13
eocBrHostDHCPTable OBJECT-TYPE
       SYNTAX SEQUENCE OF EoCBrHostDHCPEntry
       MAX-ACCESS not-accessible
       STATUS current
       DESCRIPTION
               "A table that contains host device DHCP gleaning information behind each EP. "
       ::= { eocBrIPGroup 13}

eocBrHostDHCPEntry OBJECT-TYPE
       SYNTAX EoCBrHostDHCPEntry
       MAX-ACCESS not-accessible
       STATUS current
       DESCRIPTION
               "An entry in the gleaning host DHCP list table. "
       INDEX { eocBrHostDHCPIndex }
       ::= { eocBrHostDHCPTable 1 }

EoCBrHostDHCPEntry ::= SEQUENCE {
               eocBrHostDHCPIndex Integer32,
--               eocBrHostDHCPValid INTEGER,              
               eocBrHostDHCPEPMac MacAddress,
               eocBrHostDHCPHostMac MacAddress,
               eocBrHostDHCPIPAddress IpAddress,
               eocBrHostDHCPLease Integer32
       }

-- 1,3,6,1,4,1,890,1,15,5,1,2,13,1,1
eocBrHostDHCPIndex OBJECT-TYPE
       SYNTAX Integer32
       MAX-ACCESS read-only
       STATUS current
       DESCRIPTION
               "The gleaning host DHCP entry index. "
       ::= { eocBrHostDHCPEntry 1}

-- 1,3,6,1,4,1,890,1,15,5,1,2,13,1,2
-- eocBrHostDHCPValid OBJECT-TYPE
--       SYNTAX INTEGER {
--            invalid(0),
--            valid(1)
--       }
--       MAX-ACCESS read-write
--       STATUS current
--       DESCRIPTION
--               "Show or control the validity of current host DHCP entry. "
--       ::= { eocBrHostDHCPEntry 2}

-- 1,3,6,1,4,1,890,1,15,5,1,2,13,1,3
eocBrHostDHCPEPMac OBJECT-TYPE
       SYNTAX MacAddress
       MAX-ACCESS read-only
       STATUS current
       DESCRIPTION
               "EP device Mac address of current attached host DHCP entry. "
       ::= { eocBrHostDHCPEntry 3}

-- 1,3,6,1,4,1,890,1,15,5,1,2,13,1,4
eocBrHostDHCPHostMac OBJECT-TYPE
       SYNTAX MacAddress
       MAX-ACCESS read-only
       STATUS current
       DESCRIPTION
               "Host Mac address of current host DHCP entry. "
       ::= { eocBrHostDHCPEntry 4}

-- 1,3,6,1,4,1,890,1,15,5,1,2,13,1,5
eocBrHostDHCPIPAddress OBJECT-TYPE
       SYNTAX IpAddress
       MAX-ACCESS read-only
       STATUS current
       DESCRIPTION
               "IP address of current host DHCP entry. "
       ::= { eocBrHostDHCPEntry 5}

-- 1,3,6,1,4,1,890,1,15,5,1,2,13,1,6
eocBrHostDHCPLease OBJECT-TYPE
       SYNTAX Integer32
       MAX-ACCESS read-only
       STATUS current
       DESCRIPTION
               "Remained lease time of current host DHCP entry. "
       ::= { eocBrHostDHCPEntry 6}                  

-- ----------------------------------------------------------------------------
-- 1,3,6,1,4,1,890,1,15,5,1,2,15
eocBrAutoConfig OBJECT-TYPE
       SYNTAX INTEGER {
               disable(0),
               enable(1)             
       }
       MAX-ACCESS read-write
       STATUS current
       DESCRIPTION
               "Enable the Auto-Config function or not. While enabled, bridge will try to retrieve
                the Master and all connected EP config files from the designated Auto-Config 
                directory 'eocBrAutoConfigTFTPExtensionPath' at server 
                'eocBrAutoConfigTFTPServer' via TFTP. Usually the 'Extension Path' 
                and 'TFTP Server IP Address' are obtained during the DHCP client handshaking.
                 
                For example, power on the bridge, it will start DHCP client and get the 
                Auto-Config TFTP related parameters. If the Auto-Config is ON, 
                bridge then begins to retrieve the config files of Master/EP. 
                Setup Master/EP devices accordingly. "    
       ::= { eocBrIPGroup 15}
       
-- 1,3,6,1,4,1,890,1,15,5,1,2,16       
eocBrAutoConfigTFTPServerIPAddress OBJECT-TYPE
       SYNTAX IpAddress
       MAX-ACCESS read-write
       STATUS current
       DESCRIPTION
               "The IP address of the Auto-Config TFTP server, from which 
                the management bridge can Get the Master/EP config files." 
       ::= { eocBrIPGroup 16}
       
-- 1,3,6,1,4,1,890,1,15,5,1,2,17
eocBrAutoConfigTFTPExtensionPath OBJECT-TYPE
       SYNTAX DisplayString (SIZE(0..40))
       MAX-ACCESS read-write
       STATUS current
       DESCRIPTION
               "The extension directory path of files to be retrieved 
                (TFTP Get) from the Auto-Config TFTP server. "
       ::= { eocBrIPGroup 17 }
       
-- 1,3,6,1,4,1,890,1,15,5,1,2,18       
eocBrAutoConfigTFTPServer OBJECT-TYPE
       SYNTAX DisplayString (SIZE(0..32))
       MAX-ACCESS read-write
       STATUS current
       DESCRIPTION
               "FQDN or IP address of the Auto-Config TFTP server, from which 
                the management bridge can Get the Master/EP config files. "
       ::= { eocBrIPGroup 18}                              
       
-- ============================================================================
-- eocBrEtherGroup OBJECT IDENTIFIER ::= { eoc350BrMib 10 }

-- 1,3,6,1,4,1,890,1,15,5,1,10,1
eocBrEtherPort OBJECT IDENTIFIER ::= { eocBrEtherGroup 1 }

-- 1,3,6,1,4,1,890,1,15,5,1,10,1,1
eocBrPortPropTable OBJECT-TYPE       
       SYNTAX SEQUENCE OF EoCBrPortPropEntry
       MAX-ACCESS not-accessible
       STATUS current
       DESCRIPTION
               "A table that contains Ethernet port properties. "
--     ::= { eocBrPortGroup 1 }
       ::= { eocBrEtherPort 1 }
       
eocBrPortPropEntry OBJECT-TYPE
       SYNTAX EoCBrPortPropEntry
       MAX-ACCESS not-accessible
       STATUS current
       DESCRIPTION
               "An entry in the port properties table. "
       INDEX { eocBrPortPropPID }        
       ::= { eocBrPortPropTable 1 }
       
EoCBrPortPropEntry ::= SEQUENCE {
               eocBrPortPropPID Integer32,
               eocBrPortPropType INTEGER,
               eocBrPortPropConfig INTEGER,
               eocBrPortPropLinkStatus INTEGER,
--             eocBrPortPropFlowCtrl INTEGER,
               eocBrPortPropInRateCtrl INTEGER,
               eocBrPortPropInRate INTEGER,
               eocBrPortPropOutRateCtrl INTEGER,
               eocBrPortPropOutRate INTEGER
--             eocBrPortPropEnableCtrl INTEGER
       }
       
-- 1,3,6,1,4,1,890,1,15,5,1,3,1,1,1       
eocBrPortPropPID OBJECT-TYPE
       SYNTAX Integer32
       MAX-ACCESS read-only
       STATUS current
       DESCRIPTION
               "Port index. "
       ::= { eocBrPortPropEntry 1 }
              
-- 1,3,6,1,4,1,890,1,15,5,1,3,1,1,2
eocBrPortPropType OBJECT-TYPE
       SYNTAX INTEGER {
               ethernet(0),
               coax(1),
               phoneLine(2)               
       }
       MAX-ACCESS read-only
       STATUS current
       DESCRIPTION
               "Port type. "
       ::= { eocBrPortPropEntry 2 }

-- 1,3,6,1,4,1,890,1,15,5,1,3,1,1,3
eocBrPortPropConfig OBJECT-TYPE
       SYNTAX INTEGER {
               autoNegotiation(0),
               fullDuplex100Mbps(1),
               halfDuplex100Mbps(2),
               fullDuplex10Mbps(3),
               halfDuplex10Mbps(4)
       }
       MAX-ACCESS read-write
       STATUS current
       DESCRIPTION
               "Configure Ethernet port properties. "
       ::= { eocBrPortPropEntry 3}
       
-- 1,3,6,1,4,1,890,1,15,5,1,3,1,1,4
eocBrPortPropLinkStatus OBJECT-TYPE
       SYNTAX INTEGER {
               off(0),
               fullDuplex100Mbps(1),
               halfDuplex100Mbps(2),
               fullDuplex10Mbps(3),
               halfDuplex10Mbps(4),
               fullDuplex1000Mbps(5)
       }
       MAX-ACCESS read-only
       STATUS current
       DESCRIPTION
               "Ethernet port current link status. "
       ::= { eocBrPortPropEntry 4 }
       
-- 1,3,6,1,4,1,890,1,15,5,1,10,1,1,6       
eocBrPortPropInRateCtrl OBJECT-TYPE       
       SYNTAX INTEGER {
               disable(0),
               enable(1)
       }       
       MAX-ACCESS read-write
       STATUS current
       DESCRIPTION
                "Enable/disable the maximum input(ingress) rate control for the port. "
       ::= { eocBrPortPropEntry 6 }
              
-- 1,3,6,1,4,1,890,1,15,5,1,10,1,1,7       
eocBrPortPropInRate OBJECT-TYPE       
       SYNTAX INTEGER (0..3125)
       MAX-ACCESS read-write
       STATUS current
       DESCRIPTION
                "Configure the maximum input(ingress) rate in 64kbps (n*64kbps)for the port.
                 (maximum bandwidth between 0~200Mbps)  
                 For example, value '0' will shut it off and value '4' means 
                 the maximum rate is '4*64k=256kbps'. "
       ::= { eocBrPortPropEntry 7 }
       
-- 1,3,6,1,4,1,890,1,15,5,1,10,1,1,8       
eocBrPortPropOutRateCtrl OBJECT-TYPE       
       SYNTAX INTEGER {
               disable(0),
               enable(1)
       }       
       MAX-ACCESS read-write
       STATUS current
       DESCRIPTION
                "Enable/disable the maximum output(egress) rate control for the port. "
       ::= { eocBrPortPropEntry 8 }
              
-- 1,3,6,1,4,1,890,1,15,5,1,10,1,1,9       
eocBrPortPropOutRate OBJECT-TYPE       
       SYNTAX INTEGER (0..3125)
       MAX-ACCESS read-write
       STATUS current
       DESCRIPTION
               "Configure the maximum output(egress) rate in 64kbps (n*64kbps)for the port.
                (maximum bandwidth between 0~200Mbps) . 
                For ex maple, value '0' will shut it off and value '4' means 
                the maximum rate is '4*64k=256kbps'. "
       ::= { eocBrPortPropEntry 9 }       
                              
-- ----------------------------------------------------------------------------
-- 1,3,6,1,4,1,890,1,15,5,1,10,1,2
eocBrPortStatsTable OBJECT-TYPE       
       SYNTAX SEQUENCE OF EoCBrPortStatsEntry
       MAX-ACCESS not-accessible
       STATUS current
       DESCRIPTION
               "A table that contains port statistics. "
--     ::= { eocBrPortGroup 2 }
       ::= { eocBrEtherPort 2 }
       
eocBrPortStatsEntry OBJECT-TYPE
       SYNTAX EoCBrPortStatsEntry
       MAX-ACCESS not-accessible
       STATUS current
       DESCRIPTION
               "An entry in the port statistics table. "
       INDEX { eocBrPortStatsPID }
       ::= { eocBrPortStatsTable 1 }
       
EoCBrPortStatsEntry ::= SEQUENCE {
               eocBrPortStatsPID Integer32,
               eocBrPortStatsType INTEGER,
               eocBrPortStatsRxPkts Counter64,
               eocBrPortStatsRxBytes Counter64,
               eocBrPortStatsTxPkts Counter64,
               eocBrPortStatsTxBytes Counter64,
               eocBrPortStatsCollisions Counter64,
               eocBrPortStatsErrors Counter64
       }
       
-- 1,3,6,1,4,1,890,1,15,5,1,3,2,1,1       
eocBrPortStatsPID OBJECT-TYPE
       SYNTAX Integer32
       MAX-ACCESS read-only
       STATUS current
       DESCRIPTION
               "Port index. "
       ::= { eocBrPortStatsEntry 1 }
              
-- 1,3,6,1,4,1,890,1,15,5,1,3,2,1,2
eocBrPortStatsType OBJECT-TYPE
       SYNTAX INTEGER {
               ethernet(0),
               coax(1),
               phoneLine(2)
       }
       MAX-ACCESS read-only
       STATUS current
       DESCRIPTION
               "Port type. "
       ::= { eocBrPortStatsEntry 2 }

-- 1,3,6,1,4,1,890,1,15,5,1,3,2,1,3
eocBrPortStatsRxPkts OBJECT-TYPE
       SYNTAX Counter64 
       MAX-ACCESS read-only
       STATUS current
       DESCRIPTION
               "Port statistics. "
       ::= { eocBrPortStatsEntry 3 }
       
-- 1,3,6,1,4,1,890,1,15,5,1,3,2,1,4
eocBrPortStatsRxBytes OBJECT-TYPE
       SYNTAX Counter64 
       MAX-ACCESS read-only
       STATUS current
       DESCRIPTION
               "Port statistics. "
       ::= { eocBrPortStatsEntry 4 }
              
-- 1,3,6,1,4,1,890,1,15,5,1,3,2,1,5
eocBrPortStatsTxPkts OBJECT-TYPE
       SYNTAX Counter64 
       MAX-ACCESS read-only
       STATUS current
       DESCRIPTION
               "Port statistics. "
       ::= { eocBrPortStatsEntry 5 }
       
-- 1,3,6,1,4,1,890,1,15,5,1,3,2,1,6
eocBrPortStatsTxBytes OBJECT-TYPE
       SYNTAX Counter64 
       MAX-ACCESS read-only
       STATUS current
       DESCRIPTION
               "Port statistics. "
       ::= { eocBrPortStatsEntry 6 } 
             
-- 1,3,6,1,4,1,890,1,15,5,1,3,2,1,7
eocBrPortStatsCollisions OBJECT-TYPE
       SYNTAX Counter64 
       MAX-ACCESS read-only
       STATUS current
       DESCRIPTION
               "Port statistics. "
       ::= { eocBrPortStatsEntry 7 }
       
-- 1,3,6,1,4,1,890,1,15,5,1,3,2,1,8
eocBrPortStatsErrors OBJECT-TYPE
       SYNTAX Counter64 
       MAX-ACCESS read-only
       STATUS current
       DESCRIPTION
               "Port statistics. "
       ::= { eocBrPortStatsEntry 8 }
       
-- ----------------------------------------------------------------------------
-- eocBrEtherGroup(10).eocBrEtherPort(1)

-- 1,3,6,1,4,1,890,1,15,5,1,10,1,3
eocBrStatsCtrl OBJECT IDENTIFIER ::= { eocBrEtherPort 3 }

-- 1,3,6,1,4,1,890,1,15,5,1,10,1,3,1  
eocBrStatsCtrlReset OBJECT-TYPE
       SYNTAX INTEGER {
            idle(0), 
            activate(1)
       }
       MAX-ACCESS read-write
       STATUS current
       DESCRIPTION
               "To clear/reset statistics, the SNMP manager need to set the
                value to activate(1); and submit to the bridge to clear all
                statistics. The value will back to idle(0) once reset has completed. "
       ::= { eocBrStatsCtrl 1 }
       
-- 1,3,6,1,4,1,890,1,15,5,1,10,1,3,2 
eocBrStatsCtrlRefresh OBJECT-TYPE
       SYNTAX INTEGER {
            idle(0), 
            activate(1)
       }
       MAX-ACCESS read-write
       STATUS current
       DESCRIPTION
               "To refresh/reload statistics, the SNMP manager need to set the
                value to activate(1); and submit to the bridge to refresh all
                statistics. The value will back to idle(0) once completed. "
       ::= { eocBrStatsCtrl 2 }
                      
-- ============================================================================
-- eocBrAdminGroup OBJECT IDENTIFIER ::= { eoc350BrMib 4 }

-- 1,3,6,1,4,1,890,1,15,5,1,4,1
eocBrAccountTable OBJECT-TYPE       
       SYNTAX SEQUENCE OF EoCBrAccountEntry
       MAX-ACCESS not-accessible
       STATUS current
       DESCRIPTION
               "A table that contains administrator account information. "
       ::= { eocBrAdminGroup 1 }
       
eocBrAccountEntry OBJECT-TYPE
       SYNTAX EoCBrAccountEntry
       MAX-ACCESS not-accessible
       STATUS current
       DESCRIPTION
               "An entry in the administrator account table. "
       INDEX { eocBrAccountIndex }        
       ::= { eocBrAccountTable 1 }
       
EoCBrAccountEntry ::= SEQUENCE {
               eocBrAccountIndex Integer32,
               eocBrAccountName DisplayString,
               eocBrAccountPasswd DisplayString,
               eocBrAccountPrivilege INTEGER,
               eocBrAccountRowStatus RowStatus
       }
       
-- 1,3,6,1,4,1,890,1,15,5,1,4,1,1,1       
eocBrAccountIndex OBJECT-TYPE
       SYNTAX Integer32
       MAX-ACCESS read-only
       STATUS current
       DESCRIPTION
               "Account index. "
       ::= { eocBrAccountEntry 1 }
              
-- 1,3,6,1,4,1,890,1,15,5,1,4,1,1,2
eocBrAccountName OBJECT-TYPE
       SYNTAX DisplayString (SIZE(0..8))
       MAX-ACCESS read-write
       STATUS current
       DESCRIPTION
               "Account user name. "
       ::= { eocBrAccountEntry 2 }

-- 1,3,6,1,4,1,890,1,15,5,1,4,1,1,3
eocBrAccountPasswd OBJECT-TYPE
       SYNTAX DisplayString (SIZE(0..8))
       MAX-ACCESS read-write
       STATUS current
       DESCRIPTION
               "Account password. "
       ::= { eocBrAccountEntry 3 }
       
-- 1,3,6,1,4,1,890,1,15,5,1,4,1,1,4
eocBrAccountPrivilege OBJECT-TYPE
       SYNTAX INTEGER {
               superuser(0),
               readWrite(1),
               readOnly(2)
       }
       MAX-ACCESS read-write
       STATUS current
       DESCRIPTION
               "Account privilege. "
       ::= { eocBrAccountEntry 4 }
       
-- 1,3,6,1,4,1,890,1,15,5,1,4,1,1,5
eocBrAccountRowStatus OBJECT-TYPE
       SYNTAX RowStatus
       MAX-ACCESS read-create
       STATUS current
       DESCRIPTION
               "To create, delete or modify a administrator account(one row) in this table. "
       ::= { eocBrAccountEntry 5 }           
          
-- ----------------------------------------------------------------------------
-- 1,3,6,1,4,1,890,1,15,5,1,4,2
eocBrAllowIPProtocolTable OBJECT-TYPE       
       SYNTAX SEQUENCE OF EoCBrAllowIPProtocolEntry
       MAX-ACCESS not-accessible
       STATUS current
       DESCRIPTION
               "A table that contains permitted source IP addresses with allowable protocols to access the bridge. "
       ::= { eocBrAdminGroup 2 }
       
eocBrAllowIPProtocolEntry OBJECT-TYPE
       SYNTAX EoCBrAllowIPProtocolEntry
       MAX-ACCESS not-accessible
       STATUS current
       DESCRIPTION
               "An entry for permitted source IP address and protocol to access the bridge. "
       INDEX { eocBrAllowIndex }
       ::= { eocBrAllowIPProtocolTable 1 }
       
EoCBrAllowIPProtocolEntry ::= SEQUENCE {
               eocBrAllowIndex Integer32,
               eocBrAllowIPAddress IpAddress,
               eocBrAllowSubnetMask IpAddress,
               eocBrAllowTelnet INTEGER,
               eocBrAllowHttp INTEGER,
               eocBrAllowSnmp INTEGER,
               eocBrAllowIcmpPing INTEGER,
               eocBrAllowRowStatus RowStatus
       }
       
-- 1,3,6,1,4,1,890,1,15,5,1,4,2,1,1       
eocBrAllowIndex OBJECT-TYPE
       SYNTAX Integer32
       MAX-ACCESS read-only
       STATUS current
       DESCRIPTION
               "Allowed host index. "
       ::= { eocBrAllowIPProtocolEntry 1 }
              
-- 1,3,6,1,4,1,890,1,15,5,1,4,2,1,2
eocBrAllowIPAddress OBJECT-TYPE
       SYNTAX IpAddress
       MAX-ACCESS read-write
       STATUS current
       DESCRIPTION
               "Specify the permitted source IP address. "
       ::= { eocBrAllowIPProtocolEntry 2 }

-- 1,3,6,1,4,1,890,1,15,5,1,4,2,1,3
eocBrAllowSubnetMask OBJECT-TYPE
       SYNTAX IpAddress 
       MAX-ACCESS read-write
       STATUS current
       DESCRIPTION
               "Specify the permitted subnet. "
       ::= { eocBrAllowIPProtocolEntry 3 }
       
-- 1,3,6,1,4,1,890,1,15,5,1,4,2,1,4
eocBrAllowTelnet OBJECT-TYPE
       SYNTAX INTEGER {
               deny(0),
               permit(1)
       }
       MAX-ACCESS read-write
       STATUS current
       DESCRIPTION
               "Allow TELNET or not. "
       ::= { eocBrAllowIPProtocolEntry 4 }
              
-- 1,3,6,1,4,1,890,1,15,5,1,4,2,1,5
eocBrAllowHttp OBJECT-TYPE
       SYNTAX INTEGER {
               deny(0),
               permit(1)
       }
       MAX-ACCESS read-write
       STATUS current
       DESCRIPTION
               "Allow HTTP or not. "
       ::= { eocBrAllowIPProtocolEntry 5}
       
-- 1,3,6,1,4,1,890,1,15,5,1,4,2,1,6 read-write ? read-only ?
eocBrAllowSnmp OBJECT-TYPE
       SYNTAX INTEGER {
               deny(0),
               permit(1)
       }
       MAX-ACCESS read-write
       STATUS current
       DESCRIPTION
               "Allow SNMP or not. "
       ::= { eocBrAllowIPProtocolEntry 6 } 
             
-- 1,3,6,1,4,1,890,1,15,5,1,4,2,1,7
eocBrAllowIcmpPing OBJECT-TYPE
       SYNTAX INTEGER {
               deny(0),
               permit(1)
       }
       MAX-ACCESS read-write
       STATUS current
       DESCRIPTION
               "Allow ping or not. "
       ::= { eocBrAllowIPProtocolEntry 7 }
       
-- 1,3,6,1,4,1,890,1,15,5,1,4,2,1,8
eocBrAllowRowStatus OBJECT-TYPE
       SYNTAX RowStatus
       MAX-ACCESS read-create
       STATUS current
       DESCRIPTION
               "To create, delete or modify a row in this table. "
       ::= { eocBrAllowIPProtocolEntry 8 }

-- ----------------------------------------------------------------------------
-- 1,3,6,1,4,1,890,1,15,5,1,4,3
eocBrStaticMacTable OBJECT-TYPE       
       SYNTAX SEQUENCE OF EoCBrStaticMacEntry
       MAX-ACCESS not-accessible
       STATUS current
       DESCRIPTION
               "A table that contains static Mac addresses binding to specific Ethernet port of the bridge. "
       ::= { eocBrAdminGroup 3 }
       
eocBrStaticMacEntry OBJECT-TYPE
       SYNTAX EoCBrStaticMacEntry
       MAX-ACCESS not-accessible
       STATUS current
       DESCRIPTION
               "An entry for static Mac. "
       INDEX { eocBrStaticMacIndex }
       ::= { eocBrStaticMacTable 1 }
       
EoCBrStaticMacEntry ::= SEQUENCE {
               eocBrStaticMacIndex Integer32,
               eocBrStaticMacAddress MacAddress,
               eocBrStaticMacBindingPort INTEGER,
               eocBrStaticMacRowStatus RowStatus
       }
       
-- 1,3,6,1,4,1,890,1,15,5,1,4,3,1,1       
eocBrStaticMacIndex OBJECT-TYPE
       SYNTAX Integer32
       MAX-ACCESS read-only
       STATUS current
       DESCRIPTION
               "Static Mac index. "
       ::= { eocBrStaticMacEntry 1 }
              
-- 1,3,6,1,4,1,890,1,15,5,1,4,3,1,2
eocBrStaticMacAddress OBJECT-TYPE
       SYNTAX MacAddress
       MAX-ACCESS read-write
       STATUS current
       DESCRIPTION
               "Specify the static Mac address. "
       ::= { eocBrStaticMacEntry 2 }

-- 1,3,6,1,4,1,890,1,15,5,1,4,3,1,3
eocBrStaticMacBindingPort OBJECT-TYPE
       SYNTAX INTEGER {
               lan1(1),
               lan2(2)
       } 
       MAX-ACCESS read-write
       STATUS current
       DESCRIPTION
               "Specify the static Mac binding Ethernet port index."
       ::= { eocBrStaticMacEntry 3 }
       
-- 1,3,6,1,4,1,890,1,15,5,1,4,3,1,4
eocBrStaticMacRowStatus OBJECT-TYPE
       SYNTAX RowStatus
       MAX-ACCESS read-create
       STATUS current
       DESCRIPTION
               "To create, delete or modify a row in this table. "
       ::= { eocBrStaticMacEntry 4 }
                     
-- ============================================================================
-- eocBrServiceGroup OBJECT IDENTIFIER ::= { eoc350BrMib 5 }

-- 1,3,6,1,4,1,890,1,15,5,1,5,1
eocBrTelnet OBJECT IDENTIFIER ::= { eocBrServiceGroup 1 }

-- 1,3,6,1,4,1,890,1,15,5,1,5,1,1
eocBrTelnetEnableCtrl OBJECT-TYPE       
       SYNTAX INTEGER {
               disable(0),
               enable(1)
       }
       MAX-ACCESS read-write
       STATUS current
       DESCRIPTION
               "Activate TELNET server or not. "
       ::= { eocBrTelnet 1 }
       
-- 1,3,6,1,4,1,890,1,15,5,1,5,1,2       
eocBrTelnetPortNum OBJECT-TYPE       
       SYNTAX INTEGER (0..65535)
       MAX-ACCESS read-write
       STATUS current
       DESCRIPTION
               "TELNET server listen port number. "
       ::= { eocBrTelnet 2 }
       
-- 1,3,6,1,4,1,890,1,15,5,1,5,1,3      
eocBrTelnetExpiryInSeconds OBJECT-TYPE       
       SYNTAX INTEGER (0..65535)
       MAX-ACCESS read-write
       STATUS current
       DESCRIPTION
               "TELNET server idle timer (in seconds), logout automatically if expired. "
       ::= { eocBrTelnet 3 }
       
-- ----------------------------------------------------------------------------
-- 1,3,6,1,4,1,890,1,15,5,1,5,2
eocBrHttp OBJECT IDENTIFIER ::= { eocBrServiceGroup 2 }

-- 1,3,6,1,4,1,890,1,15,5,1,5,2,1
eocBrHttpEnableCtrl OBJECT-TYPE       
       SYNTAX INTEGER {
               disable(0),
               enable(1)
       }
       MAX-ACCESS read-write
       STATUS current
       DESCRIPTION
               "Activate HTTP server or not. "
       ::= { eocBrHttp 1 }
       
-- 1,3,6,1,4,1,890,1,15,5,1,5,2,2       
eocBrHttpPortNum OBJECT-TYPE       
       SYNTAX INTEGER (0..65535)
       MAX-ACCESS read-write
       STATUS current
       DESCRIPTION
               "HTTP server listen port number. "
       ::= { eocBrHttp 2 }

-- ----------------------------------------------------------------------------
-- 1,3,6,1,4,1,890,1,15,5,1,5,3
eocBrSnmp OBJECT IDENTIFIER ::= { eocBrServiceGroup 3 }

-- 1,3,6,1,4,1,890,1,15,5,1,5,3,1
eocBrSnmpEnableCtrl OBJECT-TYPE         
       SYNTAX INTEGER {
               disable(0),
               enable(1)
       }
       MAX-ACCESS read-only
       STATUS current
       DESCRIPTION
               "Activate SNMP agent or not. "
       ::= { eocBrSnmp 1 }
       
-- 1,3,6,1,4,1,890,1,15,5,1,5,3,2
eocBrSnmpPortNum OBJECT-TYPE       
       SYNTAX INTEGER (0..65535)
       MAX-ACCESS read-only
       STATUS current
       DESCRIPTION
               "SNMP agent listen port number. "
       ::= { eocBrSnmp 2 }
       
-- 1,3,6,1,4,1,890,1,15,5,1,5,3,3
eocBrSnmpName OBJECT-TYPE       
       SYNTAX DisplayString (SIZE(0..16))
       MAX-ACCESS read-write
       STATUS current
       DESCRIPTION
               "SNMP managed bridge name. "
       ::= { eocBrSnmp 3 }
       
-- 1,3,6,1,4,1,890,1,15,5,1,5,3,4
eocBrSnmpContact OBJECT-TYPE       
       SYNTAX DisplayString (SIZE(0..16))
       MAX-ACCESS read-write
       STATUS current
       DESCRIPTION
               "SNMP managed bridge contact information. "
       ::= { eocBrSnmp 4 } 
        
-- 1,3,6,1,4,1,890,1,15,5,1,5,3,5
eocBrSnmpLocation OBJECT-TYPE       
       SYNTAX DisplayString (SIZE(0..16))
       MAX-ACCESS read-write
       STATUS current
       DESCRIPTION
               "SNMP managed bridge location information. "
       ::= { eocBrSnmp 5 }  
       
-- 1,3,6,1,4,1,890,1,15,5,1,5,3,6
eocBrSnmpReadWriteCommunity OBJECT-TYPE       
       SYNTAX DisplayString (SIZE(0..16))
       MAX-ACCESS read-write
       STATUS current
       DESCRIPTION
               "SNMP managed bridge read-write community. "
       ::= { eocBrSnmp 6 }
                        
-- 1,3,6,1,4,1,890,1,15,5,1,5,3,7
eocBrSnmpReadOnlyCommunity OBJECT-TYPE       
       SYNTAX DisplayString (SIZE(0..16))
       MAX-ACCESS read-write
       STATUS current
       DESCRIPTION
              "SNMP managed bridge read-only community. "
       ::= { eocBrSnmp 7} 

-- ----------------------------------------------------------------------------
-- 1,3,6,1,4,1,890,1,15,5,1,5,3,8
eocBrSnmpTrapEnableTable OBJECT-TYPE       
       SYNTAX SEQUENCE OF EoCBrSnmpTrapEnableEntry
       MAX-ACCESS not-accessible
       STATUS current
       DESCRIPTION
               "A table that turn on/off specific SNMP trap service. "             
       ::= { eocBrSnmp 8 }
       
eocBrSnmpTrapEnableEntry OBJECT-TYPE
       SYNTAX EoCBrSnmpTrapEnableEntry
       MAX-ACCESS not-accessible
       STATUS current
       DESCRIPTION
               "An entry that turn on/off specific SNMP trap service. "
       INDEX { eocBrSnmpTrapEnableIndex }          
       ::= { eocBrSnmpTrapEnableTable 1 }
       
EoCBrSnmpTrapEnableEntry ::= SEQUENCE {
               eocBrSnmpTrapEnableIndex Integer32,
               eocBrSnmpTrapEnableType INTEGER,
               eocBrSnmpTrapEnableCtrl INTEGER
       }
       
-- 1,3,6,1,4,1,890,1,15,5,1,5,3,8,1,1       
eocBrSnmpTrapEnableIndex OBJECT-TYPE
       SYNTAX Integer32
       MAX-ACCESS read-only
       STATUS current
       DESCRIPTION
               "SNMP trap type index to be enabled or disabled . "
       ::= { eocBrSnmpTrapEnableEntry 1 }
              
-- 1,3,6,1,4,1,890,1,15,5,1,5,3,8,1,2       
eocBrSnmpTrapEnableType OBJECT-TYPE
       SYNTAX INTEGER {
               logInOut(0),
               upgrade(1),
               epStatus(2),
               epDiagnosis(3),
               dhcp(4),
               autoConfig(5)
       }
       MAX-ACCESS read-only
       STATUS current
       DESCRIPTION
               "SNMP trap type to be enabled or disabled . "
       ::= { eocBrSnmpTrapEnableEntry 2 }
              
-- 1,3,6,1,4,1,890,1,15,5,1,5,3,8,1,3
eocBrSnmpTrapEnableCtrl OBJECT-TYPE
      SYNTAX INTEGER {
              disable(0),
              enable(1)
      }
      MAX-ACCESS read-write
      STATUS current
      DESCRIPTION
              "Enable or disable this SNMP trap type. "
      ::= { eocBrSnmpTrapEnableEntry 3 }
           
-- ----------------------------------------------------------------------------
-- 1,3,6,1,4,1,890,1,15,5,1,5,3,9
eocBrSnmpTrapTable OBJECT-TYPE       
       SYNTAX SEQUENCE OF EoCBrSnmpTrapEntry
       MAX-ACCESS not-accessible
       STATUS current
       DESCRIPTION
               "A table that contains SNMP trap service information. "             
       ::= { eocBrSnmp 9 }
       
eocBrSnmpTrapEntry OBJECT-TYPE
       SYNTAX EoCBrSnmpTrapEntry
       MAX-ACCESS not-accessible
       STATUS current
       DESCRIPTION
               "An entry for SNMP trap service. "
       INDEX { eocBrSnmpTrapIndex }          
       ::= { eocBrSnmpTrapTable 1 }
       
EoCBrSnmpTrapEntry ::= SEQUENCE {
               eocBrSnmpTrapIndex Integer32,
--             eocBrSnmpTrapEnableCtrl INTEGER,
               eocBrSnmpTrapServer DisplayString,
--             eocBrSnmpTrapIPAddress IpAddress,
               eocBrSnmpTrapPortNum INTEGER,              
               eocBrSnmpTrapCommunity DisplayString,
               eocBrSnmpTrapRowStatus RowStatus
       }
       
-- 1,3,6,1,4,1,890,1,15,5,1,5,3,9,1,1       
eocBrSnmpTrapIndex OBJECT-TYPE
       SYNTAX Integer32
       MAX-ACCESS read-only
       STATUS current
       DESCRIPTION
               "SNMP trap target index. "
       ::= { eocBrSnmpTrapEntry 1 }
              
-- 1,3,6,1,4,1,890,1,15,5,1,5,3,9,1,2
eocBrSnmpTrapServer OBJECT-TYPE       
       SYNTAX DisplayString (SIZE(0..32))
       MAX-ACCESS read-write
       STATUS current
       DESCRIPTION
               "Destined SNMP trap server name, FQDN or IP address. "
       ::= { eocBrSnmpTrapEntry 2 }

-- 1,3,6,1,4,1,890,1,15,5,1,5,3,9,1,3
-- eocBrSnmpTrapIPAddress OBJECT-TYPE
--        SYNTAX IpAddress 
--        MAX-ACCESS read-write
--        STATUS current
--        DESCRIPTION
--                "Destined SNMP trap server IP address. "
--        ::= { eocBrSnmpTrapEntry 3 }
       
-- 1,3,6,1,4,1,890,1,15,5,1,5,3,9,1,4                   
eocBrSnmpTrapPortNum OBJECT-TYPE       
       SYNTAX INTEGER (0..65535)
       MAX-ACCESS read-write
       STATUS current
       DESCRIPTION
               "SNMP trap UDP port number. "
       ::= { eocBrSnmpTrapEntry 4 }
       
-- 1,3,6,1,4,1,890,1,15,5,1,5,3,9,1,5
eocBrSnmpTrapCommunity OBJECT-TYPE       
       SYNTAX DisplayString (SIZE(0..16))
       MAX-ACCESS read-write
       STATUS current
       DESCRIPTION
               "Community for this SNMP trap.  "
       ::= { eocBrSnmpTrapEntry 5 }
             
-- 1,3,6,1,4,1,890,1,15,5,1,5,3,9,1,6
eocBrSnmpTrapRowStatus OBJECT-TYPE
       SYNTAX RowStatus
       MAX-ACCESS read-create
       STATUS current
       DESCRIPTION
               "To create, delete or modify a SNMP trap entry(one row) in this table. "
       ::= { eocBrSnmpTrapEntry 6 }
       
-- ----------------------------------------------------------------------------
-- 1,3,6,1,4,1,890,1,15,5,1,5,4       

eocBrSyslogTable OBJECT-TYPE       
       SYNTAX SEQUENCE OF EoCBrSyslogEntry
       MAX-ACCESS not-accessible
       STATUS current
       DESCRIPTION
               "A table that contains Syslog service information. "               
       ::= { eocBrServiceGroup 4 }
       
eocBrSyslogEntry OBJECT-TYPE
       SYNTAX EoCBrSyslogEntry
       MAX-ACCESS not-accessible
       STATUS current
       DESCRIPTION
               "An entry for Syslog service. "
       INDEX { eocBrSyslogIndex }        
       ::= { eocBrSyslogTable 1 }
       
EoCBrSyslogEntry ::= SEQUENCE {
               eocBrSyslogIndex Integer32,
--             eocBrSyslogEnableCtrl INTEGER,
               eocBrSyslogServer DisplayString,
               eocBrSyslogIPAddress IpAddress,
               eocBrSyslogSeverity INTEGER, 
               eocBrSyslogRowStatus RowStatus
       }
       
-- 1,3,6,1,4,1,890,1,15,5,1,5,4,1,1       
eocBrSyslogIndex OBJECT-TYPE
       SYNTAX Integer32
       MAX-ACCESS read-only
       STATUS current
       DESCRIPTION
               "Syslog server index. "
       ::= { eocBrSyslogEntry 1 }

-- 1,3,6,1,4,1,890,1,15,5,1,5,4,1,2
eocBrSyslogServer OBJECT-TYPE       
       SYNTAX DisplayString (SIZE(0..32))
       MAX-ACCESS read-write
       STATUS current
       DESCRIPTION
               "Destined Syslog server name, FQDN or IP address. "
       ::= { eocBrSyslogEntry 2 }

-- 1,3,6,1,4,1,890,1,15,5,1,5,4,1,3
eocBrSyslogIPAddress OBJECT-TYPE
       SYNTAX IpAddress 
       MAX-ACCESS read-write
       STATUS current
       DESCRIPTION
               "Destined Syslog server IP address. "
       ::= { eocBrSyslogEntry 3 }
       
-- 1,3,6,1,4,1,890,1,15,5,1,5,4,1,4                   
eocBrSyslogSeverity OBJECT-TYPE       
       SYNTAX INTEGER {
               emergency(0),
               alert(1),
               critical(2),
               error(3),
               warning(4),
               notice(5),
               info(6),
               debug(7)
       }
       MAX-ACCESS read-write
       STATUS current
       DESCRIPTION
               "Define the Syslog severity level for Syslog server. "
       ::= { eocBrSyslogEntry 4 }
             
-- 1,3,6,1,4,1,890,1,15,5,1,5,4,1,5
eocBrSyslogRowStatus OBJECT-TYPE
       SYNTAX RowStatus
       MAX-ACCESS read-create
       STATUS current
       DESCRIPTION
               "To create, delete or modify a Syslog server entry(one row) in this table. "
       ::= { eocBrSyslogEntry 5 }
       
-- ----------------------------------------------------------------------------
-- 1,3,6,1,4,1,890,1,15,5,1,5,6
eocBrSyslogCtrl OBJECT IDENTIFIER ::= {  eocBrServiceGroup 6 }
eocBrSyslogOverTcpUdp OBJECT-TYPE
      SYNTAX INTEGER {
              udp(0),
              tcp(1)
      }
      MAX-ACCESS read-write
      STATUS current
      DESCRIPTION
              "Running Syslog over UDP(default) or TCP. "
      ::= { eocBrSyslogCtrl 1}
      
eocBrSyslogPortNum OBJECT-TYPE       
       SYNTAX INTEGER (0..65535)
       MAX-ACCESS read-write
       STATUS current
       DESCRIPTION
               "Syslog TCP/UDP port number. "
       ::= { eocBrSyslogCtrl 2}      

-- ----------------------------------------------------------------------------
-- 1,3,6,1,4,1,890,1,15,5,1,5,5
eocBrSntp OBJECT IDENTIFIER ::= { eocBrServiceGroup 5 }

-- 1,3,6,1,4,1,890,1,15,5,1,5,5,1
eocBrSntpEnableCtrl OBJECT-TYPE         
       SYNTAX INTEGER {
               disable(0),
               enable(1)
       }
       MAX-ACCESS read-write
       STATUS current
       DESCRIPTION
               "Activate SNTP service or not. "
       ::= { eocBrSntp 1 }
       
-- 1,3,6,1,4,1,890,1,15,5,1,5,5,2
eocBrSntpPrimaryServer OBJECT-TYPE       
       SYNTAX DisplayString (SIZE(0..32))
       MAX-ACCESS read-write
       STATUS current
       DESCRIPTION
               "SNTP server 1, FQDN or IP address. "
       ::= { eocBrSntp 2 }
       
-- 1,3,6,1,4,1,890,1,15,5,1,5,5,3
eocBrSntpSecondaryServer OBJECT-TYPE       
       SYNTAX DisplayString (SIZE(0..32))
       MAX-ACCESS read-write
       STATUS current
       DESCRIPTION
               "SNTP server 2, FQDN or IP address. "
       ::= { eocBrSntp 3 }
       
-- 1,3,6,1,4,1,890,1,15,5,1,5,5,4
eocBrSntpTimeZone OBJECT-TYPE     
       SYNTAX INTEGER 
       {
               gmt(0),
               gmt-plus-0100(4),
               gmt-plus-0200(8),
               gmt-plus-0300(12),
               gmt-plus-0330(14),
               gmt-plus-0400(16),
               gmt-plus-0430(18),
               gmt-plus-0500(20),
               gmt-plus-0545(23),
               gmt-plus-0600(24),
               gmt-plus-0630(26),
               gmt-plus-0700(28),
               gmt-plus-0800(32),
               gmt-plus-0900(36),
               gmt-plus-0930(38),
               gmt-plus-1000(40),
               gmt-plus-1100(44),
               gmt-plus-1200(48),
               gmt-minus-1200(208),
               gmt-minus-1100(212),
               gmt-minus-1000(216),
               gmt-minus-0900(220),
               gmt-minus-0800(224),
               gmt-minus-0700(228),
               gmt-minus-0600(232),
               gmt-minus-0500(236),
               gmt-minus-0400(240),
               gmt-minus-0330(242),
               gmt-minus-0300(244),
               gmt-minus-0200(248),
               gmt-minus-0100(252)
       }           
       MAX-ACCESS  read-write
       STATUS current
       DESCRIPTION
               "SNTP locale time zone.gmt-plus-0800 means 'GMT + 8 hours'. 
                The value in 0~127 is ( GMT + value*15 minutes );
                value in 128~256 is ( GMT - (256-value)*15 minutes ). "
       ::= { eocBrSntp 4 }
       
-- 1,3,6,1,4,1,890,1,15,5,1,5,5,5
eocBrSntpQueryPeriodInMinutes OBJECT-TYPE       
       SYNTAX INTEGER (0..65535)
       MAX-ACCESS read-write
       STATUS current
       DESCRIPTION
               "SNTP queried period, in minutes. "
       ::= { eocBrSntp 5 }
       
-- 1,3,6,1,4,1,890,1,15,5,1,5,5,6
eocBrSntpCurrentTime OBJECT-TYPE       
       SYNTAX DisplayString (SIZE(0..32))
       MAX-ACCESS read-only
       STATUS current
       DESCRIPTION
               "SNTP queried time. "
       ::= { eocBrSntp 6 } 
                                  
-- ============================================================================

-- 1,3,6,1,4,1,890,1,15,5,1,10,2
eocBrEtherQoS OBJECT IDENTIFIER ::= { eocBrEtherGroup 2 }

eocBrTcpUdpPriTable OBJECT-TYPE       
       SYNTAX SEQUENCE OF EoCBrTcpUdpPriEntry
       MAX-ACCESS not-accessible
       STATUS current
       DESCRIPTION
               "A table that maps packets with specified TCP/UDP port number
                to prioritized Queues for QoS. "
       ::= { eocBrEtherQoS 2}
       
eocBrTcpUdpPriEntry OBJECT-TYPE
       SYNTAX EoCBrTcpUdpPriEntry
       MAX-ACCESS not-accessible
       STATUS current
       DESCRIPTION
               "An entry for mapping one specified TCP/UDP port number to
                one prioritized Queue. "
       INDEX { eocBrTcpUdpRuleNum }         
       ::= { eocBrTcpUdpPriTable 1 }
       
EoCBrTcpUdpPriEntry ::= SEQUENCE {
               eocBrTcpUdpRuleNum Integer32,
               eocBrTcpUdpEnableCtrl INTEGER,
               eocBrTcpUdpPortNum INTEGER,
               eocBrTcpUdpMappedQueue INTEGER
--             eocBrTcpUdpRowStatus RowStatus
       }
       
-- 1,3,6,1,4,1,890,1,15,5,1,6,2,2,1,1       
eocBrTcpUdpRuleNum OBJECT-TYPE
       SYNTAX Integer32
       MAX-ACCESS read-only
       STATUS current
       DESCRIPTION
               "TCP/UDP rule numbering value. "
       ::= { eocBrTcpUdpPriEntry 1 }
       
-- 1,3,6,1,4,1,890,1,15,5,1,6,2,2,1,2
eocBrTcpUdpEnableCtrl OBJECT-TYPE
        SYNTAX INTEGER {
               disable(0),
               enable(1)
       }
       MAX-ACCESS read-write
       STATUS current
       DESCRIPTION
               "Enable TCP/UDP port priority or not. "
       ::= { eocBrTcpUdpPriEntry 2 } 
                    
-- 1,3,6,1,4,1,890,1,15,5,1,6,2,2,1,3
eocBrTcpUdpPortNum OBJECT-TYPE
       SYNTAX INTEGER (0..65535)
       MAX-ACCESS read-write
       STATUS current
       DESCRIPTION
               "Specify the TCP/UDP port number to be mapped. "
       ::= { eocBrTcpUdpPriEntry 3 }

-- 1,3,6,1,4,1,890,1,15,5,1,6,2,2,1,4
eocBrTcpUdpMappedQueue OBJECT-TYPE
       SYNTAX INTEGER {
               q0(0),
               q1(1),
               q2(2),
               q3(3)
       }
       MAX-ACCESS read-write
       STATUS current
       DESCRIPTION
               "Specify the mapped Queue for the TCP/UDP port number. "
       ::= { eocBrTcpUdpPriEntry 4 }
       
-- 1,3,6,1,4,1,890,1,15,5,1,6,2,2,1,5
-- eocBrTcpUdpRowStatus OBJECT-TYPE
--       SYNTAX RowStatus
--       MAX-ACCESS read-create
--       STATUS current
--       DESCRIPTION
--               "To create, delete or modify a TCP/UDP port number 
--                priority mapping entry(one row) in this table. "
--       ::= { eocBrTcpUdpPriEntry 5 }

-- ----------------------------------------------------------------------------          
-- 1,3,6,1,4,1,890,1,15,5,1,6,2,3
eocBrQueueSchType OBJECT-TYPE
       SYNTAX INTEGER {
            strict(0), 
            wfq(1),
            mix(2)
       }
       MAX-ACCESS read-write
       STATUS current
       DESCRIPTION
                "The packets priority queue scheduling mechanism. There are 3 different
                 modes: 'Strict priority(SP)', 'Weighted fair queue(WFR)' and 'Mixed SP & WFR'.
                 SP: Packets residing in the higher priority queues transmit first. 
                     Lower priority packets transmit once these queues are emptied.
                     Highest priority Q3 goes first always, follows Q2 if Q3 is empty,
                     then Q1 and lowest Q0.
                 WFR:Each queue is assigned a service weight ratio that determines how many 
                     packets are sent from it. Weight is fixed at 8:4:2:1 for Q3:Q2:Q1:Q0.
                 MIX:Highest priority Q3 use SP, and other queues conform to WFR at 4:2:1 weight. "      
       ::= { eocBrEtherQoS 3 }
       
-- ----------------------------------------------------------------------------          
-- 1,3,6,1,4,1,890,1,15,5,1,6,2,4
eocBrPriSchemeSelect OBJECT-TYPE
       SYNTAX INTEGER {
            use8021p(0), 
            useIP(1)
       }
       MAX-ACCESS read-write
       STATUS current
       DESCRIPTION
                "Setup which packet field for priority queue mapping.
                 802.1p:Based on packet's 802.1p field for priority queue mapping. 
                        7/6 goes to Q3 (highest priority), 5/4 to Q2, 3/2 to Q1, 1/0 to Q0(lowest priority).
                 IP:    Based on packet's IP TOS/TC or DSCP field for priority queue mapping.
                        The precedence 2 bits in this field (DSCP/TOS/TC) decide the destined priority queue (Q3/Q2/Q1/Q0).
                        b'11 goes to Q3, b'10 to Q2, b01 to Q1, and b'00 to Q0. "      
       ::= { eocBrEtherQoS 4 }
                    
-- ============================================================================
-- eocBrMasterEoCGroup OBJECT IDENTIFIER ::= { eoc350BrMib 7 }     
  
-- 1,3,6,1,4,1,890,1,15,5,1,7,1
eocBrMasterMac OBJECT-TYPE
       SYNTAX MacAddress
       MAX-ACCESS read-only
       STATUS current
       DESCRIPTION
               "The Master device EoC Mac address. 
                Usually refers the managed bridge itself EoC interface. "
       ::= { eocBrMasterEoCGroup 1}
       
-- 1,3,6,1,4,1,890,1,15,5,1,7,2
eocBrMasterNote OBJECT-TYPE
       SYNTAX DisplayString (SIZE(0..16))
       MAX-ACCESS read-write
       STATUS current
       DESCRIPTION
               "Footnote for the Master device. " 
       ::= { eocBrMasterEoCGroup 2 }
                     
-- 1,3,6,1,4,1,890,1,15,5,1,7,3
eocBrMasterModel OBJECT-TYPE
       SYNTAX INTEGER {
--
-- MDU
--
                eOC350-TS    ('9076'h),
                eOC350-TS    ('9075'h),
                eOC350-TS    ('9876'h),
                eOC350-TS    ('9875'h)
       }
       MAX-ACCESS read-only
       STATUS current
       DESCRIPTION
               "The Master device model. Usually the management bridge itself. "
       ::= { eocBrMasterEoCGroup 3 }       
       
-- 1,3,6,1,4,1,890,1,15,5,1,7,4
eocBrMasterProductName OBJECT-TYPE
       SYNTAX DisplayString (SIZE(0..32))
       MAX-ACCESS read-only
       STATUS current
       DESCRIPTION
               "The Master device product name. Usually the management bridge itself. "
       ::= { eocBrMasterEoCGroup 4 }
       
-- 1,3,6,1,4,1,890,1,15,5,1,7,5
eocBrMasterWorkingPrivacyMode OBJECT-TYPE       
       SYNTAX INTEGER {
            off(0), 
            on(1)
       }
       MAX-ACCESS read-only
       STATUS current
       DESCRIPTION
               "Display the current/queried/working 'Privacy Mode' of Master device. 
                If 'Privacy Mode' is on, the Master device will check if its 'Privacy Key' 
                matches with the EP device's 'Privacy Key' to accept EP device's packets.
                If 'Privacy Mode' is off instead, Master device will accept connection 
                from EP device without checking 'Privacy Key'. "
       ::= { eocBrMasterEoCGroup 5 }  
            
-- 1,3,6,1,4,1,890,1,15,5,1,7,6
eocBrMasterSettingPrivacyMode OBJECT-TYPE       
       SYNTAX INTEGER {
            off(0), 
            on(1)
       }
       MAX-ACCESS read-write
       STATUS current
       DESCRIPTION
               "For Master device to activate 'Privacy Mode' or not ? Decide if the 
                Master device need to check EP device's 'Privacy Key' to 
                allow connection. Changed 'Privacy Mode' will take effect 
                after upgrading Master device driver. 
                (replace eocBrMasterWorkingPrivacyMode with 
                eocBrMasterSettingPrivacyMode after 
                eocBrMasterDrvUpgradeAction completes). "
       ::= { eocBrMasterEoCGroup 6} 
        
-- 1,3,6,1,4,1,890,1,15,5,1,7,7
eocBrMasterWorkingPrivacyKey OBJECT-TYPE
       SYNTAX INTEGER (0..65535)
       MAX-ACCESS read-only
       STATUS current
       DESCRIPTION
               "Display the current/queried/working 'Privacy Key' of Master device. "
       ::= { eocBrMasterEoCGroup 7 }
                   
-- 1,3,6,1,4,1,890,1,15,5,1,7,8
eocBrMasterSettingPrivacyKey OBJECT-TYPE
       SYNTAX INTEGER (0..65535)
       MAX-ACCESS read-write
       STATUS current
       DESCRIPTION
               "To setup the 'Privacy Key' for Master device 
                and other connected EP devices. Changed 'Privacy Key' will 
                take effect after upgrading 'Master/EP' device driver.
                (activate eocBrMasterDrvUpgradeAction/eocBrEPDrvUpgradeAction
                to replace eocBrMasterWorkingPrivacyKey/eocBrEPWorkingPrivacyKey with
                eocBrMasterSettingPrivacyKey). "
       ::= { eocBrMasterEoCGroup 8 }     
                      
-- 1,3,6,1,4,1,890,1,15,5,1,7,9
eocBrMasterDrvWorkingVersion OBJECT-TYPE
       SYNTAX DisplayString (SIZE(0..16))
       MAX-ACCESS read-only
       STATUS current
       DESCRIPTION
               "Identify the working/running driver version of the EoC chipset 
                resides in the Master device. Normally the bridge itself is 
                selected as the Master device. "
       ::= { eocBrMasterEoCGroup 9 }  
            
-- 1,3,6,1,4,1,890,1,15,5,1,7,10
eocBrMasterDrvUploadVersion OBJECT-TYPE
       SYNTAX DisplayString (SIZE(0..16))
       MAX-ACCESS read-only
       STATUS current
       DESCRIPTION
               "Identify the stored Master driver version intended for upgrading
                the EoC chipset of the Master device . The driver is placed in the 
                'upload' area temporarily and is uploaded by TFTP or HTTP first. "
       ::= { eocBrMasterEoCGroup 10 }                   
                    
-- 1,3,6,1,4,1,890,1,15,5,1,7,11
eocBrMasterDrvUpgradeAction OBJECT-TYPE
       SYNTAX INTEGER {
            idle(0), 
            activate(1)
       }
       MAX-ACCESS read-write
       STATUS current
       DESCRIPTION
               "To trigger upgrade operation of the Master device to replace 
                the current driver (version eocBrMasterWorkingEoCDrvVer) with
                the new uploaded driver (version eocBrMasterUploadEoCDrvVer). 
                The SNMP manager can upgrade the EoC Master device by set the 
                value to activate(1); and submit to the bridge to start 
                the upgrade procedure. The status (eocBrMasterDrvUpgradeStatus)
                will go from inProgress(1) status back to the initial 
                normalOrComplete(0) status. "
       ::= { eocBrMasterEoCGroup 11 }
       
-- 1,3,6,1,4,1,890,1,15,5,1,7,12
eocBrMasterDrvUpgradeStatus OBJECT-TYPE
       SYNTAX INTEGER {
            normalOrComplete(0), 
            inProgress(1),
            failed(2)
       }
       MAX-ACCESS read-only
       STATUS current
       DESCRIPTION
               "Status for upgrade operation of the Master device to replace 
                the current driver (version eocBrMasterWorkingEoCDrvVer) with
                the new uploaded driver (version eocBrMasterUploadEoCDrvVer). 
                The SNMP manager can upgrade the EoC Master device by set the 
                eocBrMasterDrvUpgradeAction value to activate(1); 
                and submit to the bridge to start the upgrade procedure. 
                The status (eocBrMasterDrvUpgradeStatus) will go from 
                inProgress(1) status back to the initial normalOrComplete(0) status. "
       ::= { eocBrMasterEoCGroup 12 }
              
-- 1,3,6,1,4,1,890,1,15,5,1,7,13
eocBrMasterScanEPAction OBJECT-TYPE
       SYNTAX INTEGER {
            idle(0), 
            activate(1)
       }
       MAX-ACCESS read-write
       STATUS current
       DESCRIPTION
               "To trigger scan operation issued by the Master device to find  
                all the on-line EP devices. That is, force to refresh all EP status. 
                The SNMP manager can set this value to activate(1) to start the 
                scan procedure. The status (eocBrMasterScanEPStatus) will go from 
                inProgress(1) status back to the initial normalOrComplete(0) status. "
       ::= { eocBrMasterEoCGroup 13 }
         
-- 1,3,6,1,4,1,890,1,15,5,1,7,14
eocBrMasterScanEPStatus OBJECT-TYPE
       SYNTAX INTEGER {
            normalOrComplete(0), 
            inProgress(1),
            failed(2)
       }
       MAX-ACCESS read-only
       STATUS current
       DESCRIPTION 
               "Status for scan operation issued by the Master device to find  
                all the on-line EP devices. That is, force to refresh all EP status. 
                The SNMP manager can set the eocBrMasterScanEPAction value to activate(1)
                to start the scan procedure. The status (eocBrMasterScanEPStatus)
                will go from inProgress(1) status back to the initial 
                normalOrComplete(0) status. "
       ::= { eocBrMasterEoCGroup 14 }

-- 1,3,6,1,4,1,890,1,15,5,1,7,15
eocBrMasterReboot OBJECT-TYPE
       SYNTAX INTEGER {
            idle(0), 
            activateThenReboot(1)
       }
       MAX-ACCESS read-write
       STATUS current
       DESCRIPTION
               "Activate to reboot the EoC Master device (whole EoC link). Will go back to the initial idle(0) while completes. "
       ::= { eocBrMasterEoCGroup 15 }
                                  
-- ============================================================================
-- eocBrEPEoCGroup OBJECT IDENTIFIER ::= { eoc350BrMib 8 }       

-- 1,3,6,1,4,1,890,1,15,5,1,8,1
eocBrEPTable OBJECT-TYPE       
       SYNTAX SEQUENCE OF EoCBrEPEntry
       MAX-ACCESS not-accessible
       STATUS current
       DESCRIPTION
               "A table that contains EP devices (EndPoint or Slave device) management information. "
       ::= { eocBrEPEoCGroup 1 }
       
eocBrEPEntry OBJECT-TYPE
       SYNTAX EoCBrEPEntry
       MAX-ACCESS not-accessible
       STATUS current
       DESCRIPTION
               "An entry in the EP management table. "
       INDEX { eocBrEPIndex }        
       ::= { eocBrEPTable 1 }
       
EoCBrEPEntry ::= SEQUENCE {
               eocBrEPIndex Integer32,
               eocBrEPMac MacAddress,
               eocBrEPNote DisplayString,
               eocBrEPModel INTEGER,
               eocBrEPProductName DisplayString,
               eocBrEPOnlineStatus INTEGER,
               eocBrEPHostCountLimit INTEGER,
               eocBrEPWorkingPrivacyKeyMatched INTEGER,
               eocBrEPDrvWorkingVersion DisplayString,
               eocBrEPDrvUploadVersion DisplayString,
               eocBrEPDrvUpgradeAction INTEGER,
               eocBrEPDrvUpgradeStatus INTEGER,
                         
-- complete invasive diagnosis, cease traffic temporarily                     
               eocBrEPPhyDiagAction INTEGER,
               eocBrEPPhyDiagStatus INTEGER,
               
               eocBrEPDiagDnLinkResult DisplayString,
               eocBrEPDiagUpLinkResult DisplayString,
               
-- noninvasive on-line diagnosis 
               eocBrEPOnlineDiagAction INTEGER,
               eocBrEPOnlineDiagStatus INTEGER,
         
               eocBrEPRowStatus INTEGER                      
       }
       
-- 1,3,6,1,4,1,890,1,15,5,1,8,1,1,1       
eocBrEPIndex OBJECT-TYPE
       SYNTAX Integer32
       MAX-ACCESS read-only
       STATUS current
       DESCRIPTION
               "The EP device index. "
       ::= { eocBrEPEntry 1 }
              
-- 1,3,6,1,4,1,890,1,15,5,1,8,1,1,2
eocBrEPMac OBJECT-TYPE
       SYNTAX MacAddress
       MAX-ACCESS read-only
       STATUS current
       DESCRIPTION
               "The EP device Mac address. "
       ::= { eocBrEPEntry 2 }
              
-- 1,3,6,1,4,1,890,1,15,5,1,8,1,1,3
eocBrEPNote OBJECT-TYPE
       SYNTAX DisplayString (SIZE(0..16))
       MAX-ACCESS read-write
       STATUS current
       DESCRIPTION
               "Footnote for the EP device. " 
       ::= { eocBrEPEntry 3 }
              
-- 1,3,6,1,4,1,890,1,15,5,1,8,1,1,4
eocBrEPModel OBJECT-TYPE
       SYNTAX INTEGER { 
--
-- MDU
--
                eOC350-TA    ('1073'h),
                eOC350-TA    ('1074'h),
                eOC350-TA    ('10f3'h),
                eOC350-TA    ('10f4'h),
                eOC350-TA    ('12f3'h),
                eOC350-TA    ('12f4'h)
       }
       MAX-ACCESS read-only
       STATUS current
       DESCRIPTION
               "The EP device model. "
       ::= { eocBrEPEntry 4 }       
       
-- 1,3,6,1,4,1,890,1,15,5,1,8,1,1,5
eocBrEPProductName OBJECT-TYPE
       SYNTAX DisplayString (SIZE(0..32))
       MAX-ACCESS read-only
       STATUS current
       DESCRIPTION
               "The EP device product name. "
       ::= { eocBrEPEntry 5 }
              
-- 1,3,6,1,4,1,890,1,15,5,1,8,1,1,6
eocBrEPOnlineStatus OBJECT-TYPE
       SYNTAX INTEGER {
            off(0), 
            on(1)
       }
       MAX-ACCESS read-only
       STATUS current
       DESCRIPTION
               "The EP on-line status. "
       ::= { eocBrEPEntry 6 }
                   
-- 1,3,6,1,4,1,890,1,15,5,1,8,1,1,8
eocBrEPHostCountLimit OBJECT-TYPE
       SYNTAX INTEGER (0..6)
       MAX-ACCESS read-write
       STATUS current
       DESCRIPTION
               "Specify the planned allowable maximum number of hosts 
                attached to the EP device. "
       ::= { eocBrEPEntry 8 }   
       
-- 1,3,6,1,4,1,890,1,15,5,1,8,1,1,12
eocBrEPWorkingPrivacyKeyMatched OBJECT-TYPE
       SYNTAX INTEGER {
            no(0),
            yes(1)
       }
       MAX-ACCESS read-only
       STATUS current
       DESCRIPTION
               "Display the status if the EP device's 'Privacy Key' is consistent 
                with Master device's 'Privacy Key'. If 'Privacy Mode' is on, 
                you will need the matched 'Privacy Key' for connection.
                If 'Privacy Mode' is off, the 'Privacy Key' is irrelevant. 
                Need to upgrade the EP device driver in order to let 
                the EP device have the matched 'Privacy Key' for connection. 
                (activate eocBrEPDrvUpgradeAction to replace EP device's 
                 'Privacy Key' with eocBrMasterSettingPrivacyKey). " 
       ::= { eocBrEPEntry 12 }  
                                    
-- 1,3,6,1,4,1,890,1,15,5,1,8,1,1,13
eocBrEPDrvWorkingVersion OBJECT-TYPE
       SYNTAX DisplayString (SIZE(0..16))
       MAX-ACCESS read-only
       STATUS current
       DESCRIPTION
               "The current working/running EoC driver version 
                in the connected EP device. "
       ::= { eocBrEPEntry 13 }  
            
-- 1,3,6,1,4,1,890,1,15,5,1,8,1,1,14
eocBrEPDrvUploadVersion OBJECT-TYPE
       SYNTAX DisplayString (SIZE(0..16))
       MAX-ACCESS read-only
       STATUS current
       DESCRIPTION
               "Identify the stored EP driver version intended for upgrading
                the EoC chipset of the EP device . The driver is placed in the 
                bridge 'upload' area temporarily and is uploaded by 
                TFTP or HTTP first. "
       ::= { eocBrEPEntry 14 }                   
                    
-- 1,3,6,1,4,1,890,1,15,5,1,8,1,1,15
eocBrEPDrvUpgradeAction OBJECT-TYPE
       SYNTAX INTEGER {
            idle(0), 
            activate(1)
       }
       MAX-ACCESS read-write
       STATUS current
       DESCRIPTION
               "To trigger upgrade operation of the EP devices to replace 
                the current driver (version eocBrEPWorkingEoCDrvVer) with
                the new uploaded driver (version eocBrEPUploadEoCDrvVer). 
                The SNMP manager can upgrade the EoC EP device by set the 
                value to activate(1); and submit to the bridge to start the 
                upgrade procedure. The status (eocBrEPDrvUpgradeStatus)
                will go from inProgress(1) status back to the initial 
                normalOrComplete(0) status. "
       ::= { eocBrEPEntry 15 }
       
-- 1,3,6,1,4,1,890,1,15,5,1,8,1,1,16
eocBrEPDrvUpgradeStatus OBJECT-TYPE
       SYNTAX INTEGER {
            normalOrComplete(0), 
            inProgress(1),
            failed(2)
       }
       MAX-ACCESS read-only
       STATUS current
       DESCRIPTION       
               "Status for upgrade operation of the EP devices to replace 
                the current driver (version eocBrEPWorkingEoCDrvVer) with
                the new uploaded driver (version eocBrEPUploadEoCDrvVer). 
                The SNMP manager can upgrade the EoC EP device by set the 
                eocBrEPDrvUpgradeAction value to activate(1); and submit 
                to the bridge to start the upgrade procedure. The status 
                (eocBrEPDrvUpgradeStatus) will go from inProgress(1) 
                status back to the initial normalOrComplete(0) status. "
       ::= { eocBrEPEntry 16}

-- 1,3,6,1,4,1,890,1,15,5,1,8,1,1,17
eocBrEPPhyDiagAction OBJECT-TYPE
       SYNTAX INTEGER {
            idle(0), 
            activate(1)
       }
       MAX-ACCESS read-write
       STATUS current
       DESCRIPTION
               "To trigger the physical link diagnosis operation between 
                the Master device and the current selected EP device. 
                The traffic will be ceased during the diagnosis.              
                The diagnosed results may include the SNR/LineRate/PacketErrorRate/RxPower 
                for both the DnLink:'Transmit'(Tx)-to-EP and
                UpLink:'Receive'(Rx)-from-EP operation. 
                The SNMP manager can set this value to activate(1) to 
                start the diagnosis procedure. The status (eocBrEPPhyDiagStatus)
                will go from inProgress(1) status back to the initial 
                normalOrComplete(0) status. "
       ::= { eocBrEPEntry 17 } 
       
-- 1,3,6,1,4,1,890,1,15,5,1,8,1,1,18
eocBrEPPhyDiagStatus OBJECT-TYPE
       SYNTAX INTEGER {
            normalOrComplete(0), 
            inProgress(1),
            failed(2)
       }
       MAX-ACCESS read-only
       STATUS current
       DESCRIPTION       
               "Status for the physical link diagnosis operation between 
                the Master device and the current selected EP device.
                The diagnosed results include the SNR/LineRate/PacketErrorRate/RxPower 
                for both the DnLink:'Transmit'(Tx)-to-EP and 
                UpLink:'Receive'(Rx)-from-EP operation. 
                The SNMP manager can set the eocBrEPPhyDiagAction value 
                to activate(1) to start the diagnosis procedure. The status 
                (eocBrEPPhyDiagStatus) will go from inProgress(1) status back 
                to the initial normalOrComplete(0) status. "
       ::= { eocBrEPEntry 18 }
       
-- 1,3,6,1,4,1,890,1,15,5,1,8,1,1,19
eocBrEPDiagDnLinkResult OBJECT-TYPE
       SYNTAX DisplayString (SIZE(0..64))
       MAX-ACCESS read-only
       STATUS current
       DESCRIPTION
               "The result of the DnLink:'Transmit'(Tx)-to-EP diagnosis. Include the following,
                Signal-to-Noise Ratio(SNR): The reasonable value should fall into 30dB~35dB. 
                Packet-Error-Ratio(PER): 1% means 1 error packet in 100 transmitted packets.
                Line-Rate: The payload encoded(PE) speed, for example 32*7 is 224Mbps.
                RxPWR: signal power level at EP receiving -60dBm~+15dBm. "        
       ::= { eocBrEPEntry 19 }

-- 1,3,6,1,4,1,890,1,15,5,1,8,1,1,20
eocBrEPDiagUpLinkResult OBJECT-TYPE
       SYNTAX DisplayString (SIZE(0..64))
       MAX-ACCESS read-only
       STATUS current
       DESCRIPTION
               "The result of the UpLink:'Receive'(Rx)-from-EP diagnosis. Include the following,
                Signal-to-Noise Ratio(SNR): The reasonable value should fall into 30dB~35dB. 
                Packet-Error-Ratio(PER): 1% means 1 error packet in 100 received packets.
                Line-Rate: The payload encoded(PE) speed, for example 32*7 is 224Mbps. 
                RxPWR: signal power level at Master receiving -60dBm~+15dBm. "
       ::= { eocBrEPEntry 20 }


-- 1,3,6,1,4,1,890,1,15,5,1,8,1,1,21
eocBrEPOnlineDiagAction OBJECT-TYPE
       SYNTAX INTEGER {
            idle(0), 
            activate(1)
       }
       MAX-ACCESS read-write
       STATUS current
       DESCRIPTION
               "To trigger the alive link diagnosis operation between 
                the Master device and the current selected EP device.
                Maintain the connection while running the diagnosis. 
                The diagnosed results include the on-line SNR/LineRate/RxPower 
                for both the DnLink:'Transmit'(Tx)-to-EP and 
                UpLink:'Receive'(Rx)-from-EP operation. 
                The SNMP manager can set this value to activate(1) to 
                start the diagnosis procedure. The status (eocBrEPOnlineDiagStatus)
                will go from inProgress(1) status back to the initial 
                normalOrComplete(0) status. "
       ::= { eocBrEPEntry 21 } 
       
-- 1,3,6,1,4,1,890,1,15,5,1,8,1,1,22
eocBrEPOnlineDiagStatus OBJECT-TYPE
       SYNTAX INTEGER {
            normalOrComplete(0), 
            inProgress(1),
            failed(2)
       }
       MAX-ACCESS read-only
       STATUS current
       DESCRIPTION       
               "Status for the alive diagnosis operation between 
                the Master device and the current selected EP device.
                The diagnosed results include the on-line SNR/LineRate/RxPower 
                for both the DnLink:'Transmit'(Tx)-to-EP and 
                UpLink:'Receive'(Rx)-from-EP operation. 
                The SNMP manager can set the eocBrEPOnlineDiagAction value 
                to activate(1) to start the diagnosis procedure. The status 
                (eocBrEPOnlineDiagStatus) will go from inProgress(1) status back 
                to the initial normalOrComplete(0) status. "
       ::= { eocBrEPEntry 22 }
                           
-- 1,3,6,1,4,1,890,1,15,5,1,8,1,1,27
eocBrEPRowStatus OBJECT-TYPE
       SYNTAX INTEGER {
            active(1), 
            destroy(6)
       }
       MAX-ACCESS read-write
       STATUS current
       DESCRIPTION
               "Reduced RowStatus Set to destroy/delete a EP entry (one row) in this table.
                The on-line EP ('eocBrOnlineStatus' is 'on') can not be destroyed."
       ::= { eocBrEPEntry 27 }  
       
-- ----------------------------------------------------------------------------       
-- 1,3,6,1,4,1,890,1,15,5,1,8,2
eocBrEPMacInfoTable OBJECT-TYPE
       SYNTAX SEQUENCE OF EoCBrEPMacInfoEntry
       MAX-ACCESS not-accessible
       STATUS current
       DESCRIPTION
               "A table that contains host Mac information behind each EP. "
       ::= { eocBrEPEoCGroup 2 }

eocBrEPMacInfoEntry OBJECT-TYPE
       SYNTAX EoCBrEPMacInfoEntry
       MAX-ACCESS not-accessible
       STATUS current
       DESCRIPTION
               "An entry in the EP host Mac list table. "
       INDEX { eocBrEP-Index }
       ::= { eocBrEPMacInfoTable 1 }
       
EoCBrEPMacInfoEntry ::= SEQUENCE {
               eocBrEP-Index Integer32,
               eocBrEP-MacType INTEGER,
               eocBrEP-EPMac MacAddress,
               eocBrEP-HostMac MacAddress                
       }

-- 1,3,6,1,4,1,890,1,15,5,1,8,2,1,1       
eocBrEP-Index OBJECT-TYPE
       SYNTAX Integer32
       MAX-ACCESS read-only
       STATUS current
       DESCRIPTION
               "The device Mac index. "
       ::= { eocBrEPMacInfoEntry 1 }
       
-- 1,3,6,1,4,1,890,1,15,5,1,8,2,1,2       
eocBrEP-MacType OBJECT-TYPE
       SYNTAX INTEGER {
            ep(0),
            master(1), 
            host(2)
       }
       MAX-ACCESS read-only
       STATUS current
       DESCRIPTION
               "The device Mac type. 0/1 for EoC device self Mac(EP/Master), 2 for host device (as PC)"
       ::= { eocBrEPMacInfoEntry 2 }              
              
-- 1,3,6,1,4,1,890,1,15,5,1,8,2,1,3
eocBrEP-EPMac OBJECT-TYPE
       SYNTAX MacAddress
       MAX-ACCESS read-only
       STATUS current
       DESCRIPTION
               "The EP device Mac address. "
       ::= { eocBrEPMacInfoEntry 3 }
       
-- 1,3,6,1,4,1,890,1,15,5,1,8,2,1,4
eocBrEP-HostMac OBJECT-TYPE
       SYNTAX MacAddress
       MAX-ACCESS read-only
       STATUS current
       DESCRIPTION
               "The host Mac address . "
       ::= { eocBrEPMacInfoEntry 4 }       
                     
-- ---------------------------------------------------------------------------- 
-- Scan host per EP or Scan all at once
eocBrEPScanMacInfo OBJECT IDENTIFIER ::= { eocBrEPEoCGroup 4 }

-- 1,3,6,1,4,1,890,1,15,5,1,8,4,1
eocBrEPScanMacInfoAction OBJECT-TYPE
       SYNTAX INTEGER {
            idle(0), 
            activate(1)
       }
       MAX-ACCESS read-write
       STATUS current
       DESCRIPTION
               "To trigger scan operation to refresh the EP device Mac and host Mac list table. 
                That is, force to refresh on-line host device list. 
                The SNMP manager can set this value to activate(1) to start the 
                scan procedure. The status (eocBrEP-ScanMacInfoStatus) will go from 
                inProgress(1) status back to the initial normalOrComplete(0) status. "
       ::= { eocBrEPScanMacInfo 1 }

-- Scan host per EP or Scan all at once         
-- 1,3,6,1,4,1,890,1,15,5,1,8,4,2
eocBrEPScanMacInfoStatus OBJECT-TYPE
       SYNTAX INTEGER {
            normalOrComplete(0), 
            inProgress(1),
            failed(2)
       }
       MAX-ACCESS read-only
       STATUS current
       DESCRIPTION 
               "Status for scan operation to find the EP device Mac and host Mac list table.
                That is, force to refresh on-line host device list. 
                The SNMP manager can set the (eocBrEP-ScanMacInfoAction) value to activate(1)
                to start the scan procedure. The status (eocBrEP-ScanMacInfoStatus)
                will go from inProgress(1) status back to the initial 
                normalOrComplete(0) status. "
       ::= { eocBrEPScanMacInfo 2 }  

-- ----------------------------------------------------------------------------       
-- 1,3,6,1,4,1,890,1,15,5,1,8,3
eocBrEPNetPerTable OBJECT-TYPE       
       SYNTAX SEQUENCE OF EoCBrEPNetPerEntry
       MAX-ACCESS not-accessible
       STATUS current
       DESCRIPTION
               "A table that contains EP device line condition monitored by tool NetPer. "
       ::= { eocBrEPEoCGroup 3 }
       
eocBrEPNetPerEntry OBJECT-TYPE
       SYNTAX EoCBrEPNetPerEntry
       MAX-ACCESS not-accessible
       STATUS current
       DESCRIPTION
               "An entry in the EP NetPer table. "
       INDEX { eocBrEPNetPerIndex }        
       ::= { eocBrEPNetPerTable 1 }
       
EoCBrEPNetPerEntry ::= SEQUENCE {
               eocBrEPNetPerIndex Integer32,
               eocBrEPNetPerEPMac MacAddress,
               eocBrEPNetPerDnLinkSNR Integer32,
               eocBrEPNetPerUpLinkSNR Integer32,
               eocBrEPNetPerDnLinkRate Integer32,
               eocBrEPNetPerUpLinkRate Integer32,
               eocBrEPNetPerDnLinkRxPwr INTEGER,
               eocBrEPNetPerUpLinkRxPwr INTEGER
--               eocBrEPNetPerDnLinkPktErr Integer32,
--               eocBrEPNetPerUpLinkPktErr Integer32
       }

-- 1,3,6,1,4,1,890,1,15,5,1,8,3,1,1       
eocBrEPNetPerIndex OBJECT-TYPE
       SYNTAX Integer32
       MAX-ACCESS read-only
       STATUS current
       DESCRIPTION
               "The EP device index. "
       ::= { eocBrEPNetPerEntry 1 }
       
-- 1,3,6,1,4,1,890,1,15,5,1,8,3,1,2       
eocBrEPNetPerEPMac OBJECT-TYPE
       SYNTAX MacAddress
       MAX-ACCESS read-only
       STATUS current
       DESCRIPTION
               "The EP device Mac address. "
       ::= { eocBrEPNetPerEntry 2 }              
              
-- 1,3,6,1,4,1,890,1,15,5,1,8,3,1,3
eocBrEPNetPerDnLinkSNR OBJECT-TYPE
       SYNTAX Integer32
       MAX-ACCESS read-only
       STATUS current
       DESCRIPTION
               "The diagnosed down-link SNR(Signal-to-Noise Ratio, unit dB) of the 'Transmit'(Tx) to EP operation. 
                It is equivalent to on-line Tx SNR in 'eocBrEPOnlineDiagStatus'. "
       ::= { eocBrEPNetPerEntry 3 }
       
-- 1,3,6,1,4,1,890,1,15,5,1,8,3,1,4
eocBrEPNetPerUpLinkSNR OBJECT-TYPE
       SYNTAX Integer32
       MAX-ACCESS read-only
       STATUS current
       DESCRIPTION
               "The diagnosed up-link SNR(Signal-to-Noise Ratio, unit dB) of the 'Receive'(Rx) from EP operation. 
                It is equivalent to on-line Rx SNR in 'eocBrEPOnlineDiagStatus'. "
       ::= { eocBrEPNetPerEntry 4 }
       
-- 1,3,6,1,4,1,890,1,15,5,1,8,3,1,5
eocBrEPNetPerDnLinkRate OBJECT-TYPE
       SYNTAX Integer32
       MAX-ACCESS read-only
       STATUS current
       DESCRIPTION
               "The down-link payload encoded(PE) line(phy) speed (unit Mbps) in the 'Transmit'(Tx) to EP operation.
                For example, 224 tells the Tx rate is 224Mbps. "
       ::= { eocBrEPNetPerEntry 5 }
       
-- 1,3,6,1,4,1,890,1,15,5,1,8,3,1,6
eocBrEPNetPerUpLinkRate OBJECT-TYPE
       SYNTAX Integer32
       MAX-ACCESS read-only
       STATUS current
       DESCRIPTION
               "The up-link payload encoded(PE) line(phy) speed (unit Mbps) in 'Receive'(Rx) from EP operation.
                For example, 224 tells the Rx rate is 224Mbps. "
       ::= { eocBrEPNetPerEntry 6 }       

-- 1,3,6,1,4,1,890,1,15,5,1,8,3,1,7
eocBrEPNetPerDnLinkRxPwr OBJECT-TYPE
       SYNTAX INTEGER (-127..128)
       MAX-ACCESS read-only
       STATUS current
       DESCRIPTION
               "The receiving down-link signal power level at EP side (Master Tx to EP),
                ranges -60dBm~+15dBm normally. "
       ::= { eocBrEPNetPerEntry 7 }
       
-- 1,3,6,1,4,1,890,1,15,5,1,8,3,1,8
eocBrEPNetPerUpLinkRxPwr OBJECT-TYPE
       SYNTAX INTEGER (-127..128)
       MAX-ACCESS read-only
       STATUS current
       DESCRIPTION
               "The receiving up-link signal power level at Master side (Master Rx from EP),
                ranges -60dBm~+15dBm normally. "
       ::= { eocBrEPNetPerEntry 8 }

-- ----------------------------------------------------------------------------       
-- 1,3,6,1,4,1,890,1,15,5,1,8,5
eocBrEPPayloadEncodeTable OBJECT-TYPE       
       SYNTAX SEQUENCE OF EoCBrEPPayloadEncodeEntry
       MAX-ACCESS not-accessible
       STATUS current
       DESCRIPTION
               "A table that contains EP device payload encoded channel rate. "
       ::= { eocBrEPEoCGroup 5 }
       
eocBrEPPayloadEncodeEntry OBJECT-TYPE
       SYNTAX EoCBrEPPayloadEncodeEntry
       MAX-ACCESS not-accessible
       STATUS current
       DESCRIPTION
               "An entry in the EP payload encoded channel rate table. "
       INDEX { eocBrEPPayloadEncodeIndex }        
       ::= { eocBrEPPayloadEncodeTable 1 }
       
EoCBrEPPayloadEncodeEntry ::= SEQUENCE {
               eocBrEPPayloadEncodeIndex Integer32,
               eocBrEPPayloadEncodeEPMac MacAddress,
               eocBrEPPayloadEncodeDnRate Integer32,
               eocBrEPPayloadEncodeUpRate Integer32
       }

-- 1,3,6,1,4,1,890,1,15,5,1,8,5,1,1       
eocBrEPPayloadEncodeIndex OBJECT-TYPE
       SYNTAX Integer32
       MAX-ACCESS read-only
       STATUS current
       DESCRIPTION
               "The EP device index. "
       ::= { eocBrEPPayloadEncodeEntry 1 }
       
-- 1,3,6,1,4,1,890,1,15,5,1,8,5,1,2       
eocBrEPPayloadEncodeEPMac OBJECT-TYPE
       SYNTAX MacAddress
       MAX-ACCESS read-only
       STATUS current
       DESCRIPTION
               "The EP device Mac address. "
       ::= { eocBrEPPayloadEncodeEntry 2 }              
              
-- 1,3,6,1,4,1,890,1,15,5,1,8,5,1,3
eocBrEPPayloadEncodeDnRate OBJECT-TYPE
       SYNTAX Integer32
       MAX-ACCESS read-only
       STATUS current
       DESCRIPTION
               "The down-link payload encoded channel rate(as line rate, unis is Mbps) from Master toward EP. "
       ::= { eocBrEPPayloadEncodeEntry 3 }
       
-- 1,3,6,1,4,1,890,1,15,5,1,8,5,1,4
eocBrEPPayloadEncodeUpRate OBJECT-TYPE
       SYNTAX Integer32
       MAX-ACCESS read-only
       STATUS current
       DESCRIPTION
               "The up-link payload encoded channel rate(as line rate, unit is Mbps) from EP toward Master. "
       ::= { eocBrEPPayloadEncodeEntry 4 }
                 
-- ============================================================================
-- eocBrTFTPGroup OBJECT IDENTIFIER ::= { eoc350BrMib 9 }  
     
-- 1,3,6,1,4,1,890,1,15,5,1,9,1       
eocBrTFTPServerIPAddress OBJECT-TYPE
       SYNTAX IpAddress
       MAX-ACCESS read-write
       STATUS current
       DESCRIPTION
               "The IP address of a TFTP server, from which the management bridge
                can Get the firmware/driver image file. Image file will first 
                upload to the management bridge itself, then activate the upgrade 
                procedure to replace the working image with the uploaded one.
                The TFTP Get procedure may be initiated by setting 
                the eocBrTFTPGetAction to activate(1). "
       ::= { eocBrTFTPGroup 1 }

-- 1,3,6,1,4,1,890,1,15,5,1,9,6
eocBrTFTPServer OBJECT-TYPE       
       SYNTAX DisplayString (SIZE(0..32))
       MAX-ACCESS read-write
       STATUS current
       DESCRIPTION
               "TFTP server name, FQDN or IP address. "
       ::= { eocBrTFTPGroup 6 }
              
-- 1,3,6,1,4,1,890,1,15,5,1,9,5
eocBrTFTPExtensionPath OBJECT-TYPE
       SYNTAX DisplayString (SIZE(0..40))
       MAX-ACCESS read-write
       STATUS current
       DESCRIPTION
               "The extension directory path of the file to retrieve 
                (TFTP Get) at the TFTP server whose address is given by 
                eocBrTFTPServer. "
       ::= { eocBrTFTPGroup 5 }
       
-- 1,3,6,1,4,1,890,1,15,5,1,9,2
eocBrTFTPFilename OBJECT-TYPE
       SYNTAX DisplayString (SIZE(0..32))
       MAX-ACCESS read-write
       STATUS current
       DESCRIPTION
               "The name of the firmware/driver image file to retrieve 
                (TFTP Get) at the TFTP server whose address is given by 
                eocBrTFTPServer. "
       ::= { eocBrTFTPGroup 2 }
       
-- 1,3,6,1,4,1,890,1,15,5,1,9,3       
eocBrTFTPGetAction OBJECT-TYPE
       SYNTAX INTEGER {
            idle(0), 
            activate(1)
       }
       MAX-ACCESS read-write
       STATUS current
       DESCRIPTION
               "To trigger TFTP Get operation, the SNMP manager need to set the
                value to activate(1); and submit to the bridge to start 
                the TFTP Get procedure. The status (eocBrTFTPGetStatus) will go 
                from inProgress(1) status back to the initial normalOrComplete(0)
                status. TFTP Get will attempt to retrieve a firmware/driver file 
                from the TFTP server whose address is given by eocBrTFTPServer. 
                The filename is given by eocBrTFTPFilename. Both 
                eocBrTFTPServer and eocBrTFTPFilename must be correct 
                for the TFTP operation to proceed. "
       ::= { eocBrTFTPGroup 3 }
       
-- 1,3,6,1,4,1,890,1,15,5,1,9,4       
eocBrTFTPGetStatus OBJECT-TYPE
       SYNTAX INTEGER {
            normalOrComplete(0), 
            inProgress(1),
            failed(2)
       }
       MAX-ACCESS read-only
       STATUS current
       DESCRIPTION      
               "Status for the  TFTP Get operation, the SNMP manager need to set the
                eocBrTFTPGetAction value to activate(1); and submit to the bridge 
                to start the TFTP Get procedure. The status (eocBrTFTPGetStatus)
                will go from inProgress(1) status back to the initial 
                normalOrComplete(0) status. TFTP Get will attempt to retrieve 
                a firmware/driver file from the TFTP server whose address 
                is given by eocBrTFTPServer. The filename is given by 
                eocBrTFTPFilename. Both eocBrTFTPServer and 
                eocBrTFTPFilename must be correct for the TFTP operation to proceed. "
       ::= { eocBrTFTPGroup 4 }  

-- ----------------------------------------------------------------------------
-- 1,3,6,1,4,1,890,1,15,5,1,10,3
eocBrEtherIGMPSnoop OBJECT IDENTIFIER ::= { eocBrEtherGroup 3 }

-- 1,3,6,1,4,1,890,1,15,5,1,10,3,1
eocBrIGMPSnoopEnableCtrl OBJECT-TYPE
       SYNTAX INTEGER {
            disable(0), 
            enable(1)
       }
       MAX-ACCESS read-write
       STATUS current
       DESCRIPTION
               "Enable IGMP v1/v2 Snooping or not. Not support IGMP v3 Snooping. "
       ::= { eocBrEtherIGMPSnoop 1 }

-- ----------------------------------------------------------------------------
-- 1,3,6,1,4,1,890,1,15,5,1,10,4
eocBrEtherTagVLAN OBJECT IDENTIFIER ::= { eocBrEtherGroup 4 }

-- 1,3,6,1,4,1,890,1,15,5,1,10,4,1
eocBrTagVLANEnableCtrl OBJECT-TYPE
       SYNTAX INTEGER {
            disable(0),
            enable(1)
       }
       MAX-ACCESS read-write
       STATUS current
       DESCRIPTION
               "Enable Tagged VLAN(802.1Q) or not. "
       ::= { eocBrEtherTagVLAN 1 }
     
-- ----------------------------------------------------------------------------
-- 1,3,6,1,4,1,890,1,15,5,1,10,4,2
eocBrTagPortTable OBJECT-TYPE
       SYNTAX SEQUENCE OF EoCBrTagPortEntry
       MAX-ACCESS not-accessible
       STATUS current
       DESCRIPTION
               "Table of Ethernet Tagged VLAN(802.1Q) information. "
       ::= { eocBrEtherTagVLAN 2 }

eocBrTagPortEntry OBJECT-TYPE
       SYNTAX EoCBrTagPortEntry
       MAX-ACCESS not-accessible
       STATUS current
       DESCRIPTION
               "An entry in the Ethernet Tagged VLAN(802.1Q) table. "
       INDEX {eocBrTagPortPID }
       ::= { eocBrTagPortTable 1 }

EoCBrTagPortEntry ::= SEQUENCE {
               eocBrTagPortPID Integer32,
               eocBrTagPortType INTEGER,
               eocBrTagPortPriority INTEGER,
               eocBrTagPortVID INTEGER,
               eocBrTagPortInRule INTEGER,
               eocBrTagPortOutRule INTEGER
       }

-- 1,3,6,1,4,1,890,1,15,5,1,10,4,2,1,1
eocBrTagPortPID OBJECT-TYPE
       SYNTAX Integer32
       MAX-ACCESS read-only
       STATUS current
       DESCRIPTION
               "Port index. "
       ::= { eocBrTagPortEntry 1 }

-- 1,3,6,1,4,1,890,1,15,5,1,10,4,2,1,2
eocBrTagPortType OBJECT-TYPE
       SYNTAX INTEGER {
               ethernet(0),
               coax(1),
               phoneLine(2)
       }
       MAX-ACCESS read-only
       STATUS current
       DESCRIPTION
               "Port type. "
       ::= { eocBrTagPortEntry 2 }
       
-- 1,3,6,1,4,1,890,1,15,5,1,10,4,2,1,3
eocBrTagPortPriority OBJECT-TYPE
       SYNTAX INTEGER (0..7)
       ACCESS read-write
       STATUS current
       DESCRIPTION
               "The default 802.1p priority value of current port. "
       ::= { eocBrTagPortEntry 3 }  
            
-- 1,3,6,1,4,1,890,1,15,5,1,10,4,2,1,4
eocBrTagPortVID OBJECT-TYPE
       SYNTAX INTEGER (1..4095)
       ACCESS read-write
       STATUS current
       DESCRIPTION
               "The default VLAN ID (VID) of current port. "
       ::= { eocBrTagPortEntry 4 }

-- 1,3,6,1,4,1,890,1,15,5,1,10,4,2,1,5
eocBrTagPortInRule OBJECT-TYPE
       SYNTAX INTEGER {
           all(0),
           tag(1)
       }
       ACCESS read-write
       STATUS current
       DESCRIPTION
               "Defines the 'action' (ingress rule) on packet enters current port. 
                all(0)->accept all(untagged/tagged) pkt and tag the untagged pkt.
                tag(1)->accept tagged pkt only. "
       ::= { eocBrTagPortEntry 5 }

-- 1,3,6,1,4,1,890,1,15,5,1,10,4,2,1,6
eocBrTagPortOutRule OBJECT-TYPE
       SYNTAX INTEGER {
           untag(0),
           tag(1),
           bypass(2)
       }
       ACCESS read-write
       STATUS current
       DESCRIPTION
               "Defines the 'action' (egress rule) on packet output from current port.
                untag(0)-> remove tag from tagged pkt. 
                tag(1)-> tag all output pkt.
                bypass(2)-> pass through either tagged or untagged pkt. "
       ::= { eocBrTagPortEntry 6 }

-- ----------------------------------------------------------------------------
-- 1,3,6,1,4,1,890,1,15,5,1,10,5
eocBrEtherCascadeLan OBJECT IDENTIFIER ::= { eocBrEtherGroup 5 }

-- 1,3,6,1,4,1,890,1,15,5,1,10,5,1
eocBrCascadeMode OBJECT-TYPE
       SYNTAX INTEGER {
            disable(0), 
            downLinkLAN1-upLinkLAN2(1),
            downLinkLAN2-upLinkLAN1(2),
            autoBySTP(3)
            
       }
       MAX-ACCESS read-write
       STATUS current
       DESCRIPTION
               "Enable to cascade multiple bridges via port LAN2 and LAN1, alike daisy chain. 
                mode 0: disable 
                mode 1: LAN1 as downstream Link and LAN2 as upstream link
                mode 2: LAN2 as downstream Link and LAN1 as upstream link
                mode 3: downstream Link and upstream link are decided by STP 
                        automatically (STP: spanning tree protocol) "
       ::= { eocBrEtherCascadeLan 1 }

-- ============================================================================
-- eocBrEPEtherGroup OBJECT IDENTIFIER ::= { eoc350BrMib 11 }

-- ----------------------------------------------------------------------------
-- 1,3,6,1,4,1,890,1,15,5,1,11,1
eocBrEPDesignate OBJECT IDENTIFIER ::= { eocBrEPEtherGroup 1 }

-- eocBrEPEtherGroup(11).eocBrEPDesignate(1)

-- 1,3,6,1,4,1,890,1,15,5,1,11,1,1
eocBrEPDesignateTable OBJECT-TYPE       
       SYNTAX SEQUENCE OF EoCBrEPDesignateEntry
       MAX-ACCESS not-accessible
       STATUS current
       DESCRIPTION
               "A table that contains EP for selection/choosing to be managed by 
                eocBrEPEtherGroup.eocBrEPEtherPort SNMP management items. "
       ::= { eocBrEPDesignate 1 }
       
eocBrEPDesignateEntry OBJECT-TYPE
       SYNTAX EoCBrEPDesignateEntry
       MAX-ACCESS not-accessible
       STATUS current
       DESCRIPTION
               "An entry in the EP selection/choosing table. "
       INDEX { eocBrEPDesignateEPIndex }        
       ::= { eocBrEPDesignateTable 1 }
       
EoCBrEPDesignateEntry ::= SEQUENCE {
               eocBrEPDesignateEPIndex Integer32,
               eocBrEPDesignateEPMac MacAddress, 
               eocBrEPDesignateOnlineStatus INTEGER,
               eocBrEPDesignateDeviceVersion INTEGER, 
--               eocBrEPDesignateInnerVersion INTEGER,   
               eocBrEPDesignateIsSmart INTEGER,
               eocBrEPDesignateIsTarget INTEGER
       }
       
-- 1,3,6,1,4,1,890,1,15,5,1,11,1,1,1,1
eocBrEPDesignateEPIndex OBJECT-TYPE
       SYNTAX Integer32
       MAX-ACCESS read-only
       STATUS current
       DESCRIPTION
               "Designate EP index. "
       ::= { eocBrEPDesignateEntry 1 }
       
-- 1,3,6,1,4,1,890,1,15,5,1,11,1,1,1,2
eocBrEPDesignateEPMac OBJECT-TYPE
       SYNTAX MacAddress
       MAX-ACCESS read-only
       STATUS current
       DESCRIPTION
               "The EP device Mac address. "
       ::= { eocBrEPDesignateEntry 2 }
       
-- 1,3,6,1,4,1,890,1,15,5,1,11,1,1,1,3
eocBrEPDesignateOnlineStatus OBJECT-TYPE
       SYNTAX INTEGER {
            off(0), 
            on(1)
       }
       MAX-ACCESS read-only
       STATUS current
       DESCRIPTION
               "The EP device on-line status. "
       ::= { eocBrEPDesignateEntry 3 }
       
-- 1,3,6,1,4,1,890,1,15,5,1,11,1,1,1,4
eocBrEPDesignateDeviceVersion OBJECT-TYPE
       SYNTAX INTEGER (0..65535)
       MAX-ACCESS read-only
       STATUS current
       DESCRIPTION
               "The EP device hardware version. "
       ::= { eocBrEPDesignateEntry 4 }
       
-- 1,3,6,1,4,1,890,1,15,5,1,11,1,1,1,5
-- eocBrEPDesignateInnerVersion OBJECT-TYPE
--       SYNTAX INTEGER (0..65535)
--       MAX-ACCESS read-only
--       STATUS current
--       DESCRIPTION
--               "The EP device inner version. "
--       ::= { eocBrEPDesignateEntry 5 }
              
-- 1,3,6,1,4,1,890,1,15,5,1,11,1,1,1,6
eocBrEPDesignateIsSmart OBJECT-TYPE
       SYNTAX INTEGER {
               no(0),
               yes(1),
               unknown(255)               
       }
       MAX-ACCESS read-only
       STATUS current
       DESCRIPTION
               "Is it the Smart EP ? Only the Smart EP device is configurable. "
       ::= { eocBrEPDesignateEntry 6}
       
-- 1,3,6,1,4,1,890,1,15,5,1,11,1,1,1,7
eocBrEPDesignateIsTarget OBJECT-TYPE
       SYNTAX INTEGER {
               no(0),
               yes(1)               
       }
       MAX-ACCESS read-write
       STATUS current
       DESCRIPTION
               "Choose the target -- designate the EP device for applying SNMP management 
                to its Ethernet port properties. "
       ::= { eocBrEPDesignateEntry 7 }       
       
-- ----------------------------------------------------------------------------
-- 1,3,6,1,4,1,890,1,15,5,1,11,2
eocBrEPEtherPort OBJECT IDENTIFIER ::= { eocBrEPEtherGroup 2 }

-- eocBrEPEtherGroup(11).eocBrEPEtherPort(2)

-- 1,3,6,1,4,1,890,1,15,5,1,11,2,1
eocBrEPPortPropTable OBJECT-TYPE       
       SYNTAX SEQUENCE OF EoCBrEPPortPropEntry
       MAX-ACCESS not-accessible
       STATUS current
       DESCRIPTION
               "A table that contains designated EP Ethernet port properties. "
       ::= { eocBrEPEtherPort 1 }
       
eocBrEPPortPropEntry OBJECT-TYPE
       SYNTAX EoCBrEPPortPropEntry
       MAX-ACCESS not-accessible
       STATUS current
       DESCRIPTION
               "An entry in the designated EP port properties table. "
       INDEX { eocBrEPPortPropEPIndex, eocBrEPPortPropPID }        
       ::= { eocBrEPPortPropTable 1 }
       
EoCBrEPPortPropEntry ::= SEQUENCE {
               eocBrEPPortPropEPIndex Integer32,
               eocBrEPPortPropPID Integer32,
               eocBrEPPortPropEPMac MacAddress,               
               eocBrEPPortPropType INTEGER,
               eocBrEPPortPropConfig INTEGER,
               eocBrEPPortPropLinkStatus INTEGER,
               eocBrEPPortPropFlowCtrl INTEGER,
               eocBrEPPortPropInRateCtrl INTEGER,
               eocBrEPPortPropInRate INTEGER,
               eocBrEPPortPropOutRateCtrl INTEGER,
               eocBrEPPortPropOutRate INTEGER,
               eocBrEPPortPropEnableCtrl INTEGER
       }
       
-- 1,3,6,1,4,1,890,1,15,5,1,11,2,1,1,1
eocBrEPPortPropEPIndex OBJECT-TYPE
       SYNTAX Integer32
       MAX-ACCESS read-only
       STATUS current
       DESCRIPTION
               "Designate EP index. "
       ::= { eocBrEPPortPropEntry 1 }
                            
-- 1,3,6,1,4,1,890,1,15,5,1,11,2,1,1,2       
eocBrEPPortPropPID OBJECT-TYPE
       SYNTAX Integer32
       MAX-ACCESS read-only
       STATUS current
       DESCRIPTION
               "Designated EP port index. "
       ::= { eocBrEPPortPropEntry 2 }
       
-- 1,3,6,1,4,1,890,1,15,5,1,11,2,1,1,3
eocBrEPPortPropEPMac OBJECT-TYPE
       SYNTAX MacAddress
       MAX-ACCESS read-only
       STATUS current
       DESCRIPTION
               "The designated EP device Mac address. "
       ::= { eocBrEPPortPropEntry 3 }
                     
-- 1,3,6,1,4,1,890,1,15,5,1,11,2,1,1,4
eocBrEPPortPropType OBJECT-TYPE
       SYNTAX INTEGER {
               ethernet(0),
               coax(1),
               phoneLine(2)               
       }
       MAX-ACCESS read-only
       STATUS current
       DESCRIPTION
               "Designated EP port type. "
       ::= { eocBrEPPortPropEntry 4}

-- 1,3,6,1,4,1,890,1,15,5,1,11,2,1,1,5
eocBrEPPortPropConfig OBJECT-TYPE
       SYNTAX INTEGER {
               autoNegotiation(0),
               fullDuplex100Mbps(1),
               halfDuplex100Mbps(2),
               fullDuplex10Mbps(3),
               halfDuplex10Mbps(4)
       }
       MAX-ACCESS read-write
       STATUS current
       DESCRIPTION
               "Configure designated EP Ethernet port properties. "
       ::= { eocBrEPPortPropEntry 5}
       
-- 1,3,6,1,4,1,890,1,15,5,1,11,2,1,1,6
eocBrEPPortPropLinkStatus OBJECT-TYPE
       SYNTAX INTEGER {
               off(0),
               fullDuplex100Mbps(1),
               halfDuplex100Mbps(2),
               fullDuplex10Mbps(3),
               halfDuplex10Mbps(4)
       }
       MAX-ACCESS read-only
       STATUS current
       DESCRIPTION
               "Designated EP Ethernet port current link status. "
       ::= { eocBrEPPortPropEntry 6 }
            
-- 1,3,6,1,4,1,890,1,15,5,1,11,2,1,1,7
eocBrEPPortPropFlowCtrl OBJECT-TYPE       
       SYNTAX INTEGER {
               off(0),
               on(1)
       }
       MAX-ACCESS read-write
       STATUS current
       DESCRIPTION
               "Configure designated EP Ethernet port flow control. "
       ::= { eocBrEPPortPropEntry 7 }
       
-- 1,3,6,1,4,1,890,1,15,5,1,11,2,1,1,8       
eocBrEPPortPropInRateCtrl OBJECT-TYPE       
       SYNTAX INTEGER {
               disable(0),
               enable(1)
       }       
       MAX-ACCESS read-write
       STATUS current
       DESCRIPTION
                "Enable/disable the maximum input(ingress) rate control for the designated EP port. "
       ::= { eocBrEPPortPropEntry 8 }
              
-- 1,3,6,1,4,1,890,1,15,5,1,11,2,1,1,9      
eocBrEPPortPropInRate OBJECT-TYPE       
       SYNTAX INTEGER (0..1563)
       MAX-ACCESS read-write
       STATUS current
       DESCRIPTION
                "Configure the maximum input(ingress) rate in 64kbps (n*64kbps)for the designated EP port.
                 (maximum bandwidth between 0~100Mbps)  
                 For example, value '0' will shut it off and value '4' means 
                 the maximum rate is '4*64k=256kbps'. "
       ::= { eocBrEPPortPropEntry 9 }
       
-- 1,3,6,1,4,1,890,1,15,5,1,11,2,1,1,10       
eocBrEPPortPropOutRateCtrl OBJECT-TYPE       
       SYNTAX INTEGER {
               disable(0),
               enable(1)
       }       
       MAX-ACCESS read-write
       STATUS current
       DESCRIPTION
                "Enable/disable the maximum output(egress) rate control for the designated EP port. "
       ::= { eocBrEPPortPropEntry 10 }
              
-- 1,3,6,1,4,1,890,1,15,5,1,11,2,1,1,11       
eocBrEPPortPropOutRate OBJECT-TYPE       
       SYNTAX INTEGER (0..1563)
       MAX-ACCESS read-write
       STATUS current
       DESCRIPTION
               "Configure the maximum output(egress) rate in 64kbps (n*64kbps)for the designated EP port.
                (maximum bandwidth between 0~100Mbps) . 
                For example, value '0' will shut it off and value '4' means 
                the maximum rate is '4*64k=256kbps'. "
       ::= { eocBrEPPortPropEntry 11 }       
       
-- 1,3,6,1,4,1,890,1,15,5,1,11,2,1,1,12
eocBrEPPortPropEnableCtrl OBJECT-TYPE       
       SYNTAX INTEGER {
               disable(0),
               enable(1)
       }
       MAX-ACCESS read-write
       STATUS current
       DESCRIPTION
               "Enable current designated EP Ethernet port or not. "
       ::= { eocBrEPPortPropEntry 12 }
   
-- ----------------------------------------------------------------------------
-- eocBrEPEtherGroup(11).eocBrEPEtherPort(2)

-- 1,3,6,1,4,1,890,1,15,5,1,11,2,2
eocBrEPPortStatsTable OBJECT-TYPE       
       SYNTAX SEQUENCE OF EoCBrEPPortStatsEntry
       MAX-ACCESS not-accessible
       STATUS current
       DESCRIPTION
               "A table that contains EP port statistics. "
       ::= { eocBrEPEtherPort 2 }
       
eocBrEPPortStatsEntry OBJECT-TYPE
       SYNTAX EoCBrEPPortStatsEntry
       MAX-ACCESS not-accessible
       STATUS current
       DESCRIPTION
               "An entry in the EP port statistics table. "
       INDEX { eocBrEPPortStatsEPIndex, eocBrEPPortStatsPID }
       ::= { eocBrEPPortStatsTable 1 }
       
EoCBrEPPortStatsEntry ::= SEQUENCE {
               eocBrEPPortStatsEPIndex Integer32,
               eocBrEPPortStatsPID Integer32,
               eocBrEPPortStatsEPMac MacAddress,              
               eocBrEPPortStatsType INTEGER,
               eocBrEPPortStatsRxPkts Counter32,
               eocBrEPPortStatsRxBytes Counter32,
               eocBrEPPortStatsTxPkts Counter32,
               eocBrEPPortStatsTxBytes Counter32,
               eocBrEPPortStatsCollisions Counter32,
               eocBrEPPortStatsErrors Counter32
       }

-- 1,3,6,1,4,1,890,1,15,5,1,11,2,2,1,1
eocBrEPPortStatsEPIndex OBJECT-TYPE
       SYNTAX Integer32
       MAX-ACCESS read-only
       STATUS current
       DESCRIPTION
               "Designate EP index. "
       ::= { eocBrEPPortStatsEntry 1 }
                     
-- 1,3,6,1,4,1,890,1,15,5,1,11,2,2,1,2      
eocBrEPPortStatsPID OBJECT-TYPE
       SYNTAX Integer32
       MAX-ACCESS read-only
       STATUS current
       DESCRIPTION
               "Designated EP port index. "
       ::= { eocBrEPPortStatsEntry 2 }
       
-- 1,3,6,1,4,1,890,1,15,5,1,11,2,2,1,3
eocBrEPPortStatsEPMac OBJECT-TYPE
       SYNTAX MacAddress
       MAX-ACCESS read-only
       STATUS current
       DESCRIPTION
               "The designated EP device Mac address. "
       ::= { eocBrEPPortStatsEntry 3 }
                     
-- 1,3,6,1,4,1,890,1,15,5,1,11,2,2,1,4
eocBrEPPortStatsType OBJECT-TYPE
       SYNTAX INTEGER {
               ethernet(0),
               coax(1),
               phoneLine(2)
       }
       MAX-ACCESS read-only
       STATUS current
       DESCRIPTION
               "Designated EP port type. "
       ::= { eocBrEPPortStatsEntry 4}

-- 1,3,6,1,4,1,890,1,15,5,1,11,2,2,1,5
eocBrEPPortStatsRxPkts OBJECT-TYPE
       SYNTAX Counter32
       MAX-ACCESS read-only
       STATUS current
       DESCRIPTION
               "Designated EP port statistics. "
       ::= { eocBrEPPortStatsEntry 5 }
       
-- 1,3,6,1,4,1,890,1,15,5,1,11,2,2,1,6
eocBrEPPortStatsRxBytes OBJECT-TYPE
       SYNTAX Counter32 
       MAX-ACCESS read-only
       STATUS current
       DESCRIPTION
               "Designated EP port statistics. "
       ::= { eocBrEPPortStatsEntry 6 }
              
-- 1,3,6,1,4,1,890,1,15,5,1,11,2,2,1,7
eocBrEPPortStatsTxPkts OBJECT-TYPE
       SYNTAX Counter32 
       MAX-ACCESS read-only
       STATUS current
       DESCRIPTION
               "Designated EP port statistics. "
       ::= { eocBrEPPortStatsEntry 7 }
       
-- 1,3,6,1,4,1,890,1,15,5,1,11,2,2,1,8
eocBrEPPortStatsTxBytes OBJECT-TYPE
       SYNTAX Counter32 
       MAX-ACCESS read-only
       STATUS current
       DESCRIPTION
               "Designated EP port statistics. "
       ::= { eocBrEPPortStatsEntry 8 } 
             
-- 1,3,6,1,4,1,890,1,15,5,1,11,2,2,1,9
eocBrEPPortStatsCollisions OBJECT-TYPE
       SYNTAX Counter32 
       MAX-ACCESS read-only
       STATUS current
       DESCRIPTION
               "Designated EP port statistics. "
       ::= { eocBrEPPortStatsEntry 9 }
       
-- 1,3,6,1,4,1,890,1,15,5,1,11,2,2,1,10
eocBrEPPortStatsErrors OBJECT-TYPE
       SYNTAX Counter32 
       MAX-ACCESS read-only
       STATUS current
       DESCRIPTION
               "Designated EP port statistics. "
       ::= { eocBrEPPortStatsEntry 10 }
       
-- ----------------------------------------------------------------------------
-- eocBrEPEtherGroup(11).eocBrEPEtherPort(2)

-- 1,3,6,1,4,1,890,1,15,5,1,11,2,3
eocBrEPStatsCtrlTable OBJECT-TYPE
       SYNTAX SEQUENCE OF EoCBrEPStatsCtrlEntry
       MAX-ACCESS not-accessible
       STATUS current
       DESCRIPTION
               "A table of designated EP statistics control. "             
       ::= { eocBrEPEtherPort 3 }
       
eocBrEPStatsCtrlEntry OBJECT-TYPE
       SYNTAX EoCBrEPStatsCtrlEntry
       MAX-ACCESS not-accessible
       STATUS current
       DESCRIPTION
               "An entry in designated EP statistics control table. "
       INDEX { eocBrEPStatsCtrlEPIndex }        
       ::= { eocBrEPStatsCtrlTable 1 }
       
EoCBrEPStatsCtrlEntry ::= SEQUENCE {
               eocBrEPStatsCtrlEPIndex Integer32,
               eocBrEPStatsCtrlEPMac MacAddress,
               eocBrEPStatsCtrlReset INTEGER,
               eocBrEPStatsCtrlRefresh INTEGER
    }

-- 1,3,6,1,4,1,890,1,15,5,1,11,2,3,1,1
eocBrEPStatsCtrlEPIndex OBJECT-TYPE
       SYNTAX Integer32
       MAX-ACCESS read-only
       STATUS current
       DESCRIPTION
               "Designate EP index. "
       ::= { eocBrEPStatsCtrlEntry 1 }
           
-- 1,3,6,1,4,1,890,1,15,5,1,11,2,3,1,2
eocBrEPStatsCtrlEPMac OBJECT-TYPE
       SYNTAX MacAddress
       MAX-ACCESS read-only
       STATUS current
       DESCRIPTION
               "The designated EP device Mac address. "
       ::= { eocBrEPStatsCtrlEntry 2 }

-- 1,3,6,1,4,1,890,1,15,5,1,11,2,3,1,3 
eocBrEPStatsCtrlReset OBJECT-TYPE
       SYNTAX INTEGER {
            idle(0), 
            activate(1)
       }
       MAX-ACCESS read-write
       STATUS current
       DESCRIPTION
               "To clear/reset designated EP statistics, the SNMP manager need to set the
                value to activate(1); and submit to the bridge to clear designated EP 
                statistics. The value will back to idle(0) once reset has completed. "
       ::= { eocBrEPStatsCtrlEntry 3 }
       
-- 1,3,6,1,4,1,890,1,15,5,1,11,2,3,1,4 
eocBrEPStatsCtrlRefresh OBJECT-TYPE
       SYNTAX INTEGER {
            idle(0), 
            activate(1)
       }
       MAX-ACCESS read-write
       STATUS current
       DESCRIPTION
               "To refresh/reload designated EP statistics, the SNMP manager need to set the
                value to activate(1); and submit to the bridge to refresh designated EP 
                statistics. The value will back to idle(0) once completed. "
       ::= { eocBrEPStatsCtrlEntry 4 }

      
-- ----------------------------------------------------------------------------
-- 1,3,6,1,4,1,890,1,15,5,1,11,3
eocBrEPEtherQoS OBJECT IDENTIFIER ::= { eocBrEPEtherGroup 3 }
      
-- ----------------------------------------------------------------------------
-- eocBrEPEtherGroup(11).eocBrEPEtherQoS(3)

-- 1,3,6,1,4,1,890,1,15,5,1,11,3,2
eocBrEPTcpUdpPriTable OBJECT-TYPE       
       SYNTAX SEQUENCE OF EoCBrEPTcpUdpPriEntry
       MAX-ACCESS not-accessible
       STATUS current
       DESCRIPTION
               "A table that maps packets with specified TCP/UDP port number
                to prioritized Queues for QoS in designated EP. "         
       ::= { eocBrEPEtherQoS 2}
       
eocBrEPTcpUdpPriEntry OBJECT-TYPE
       SYNTAX EoCBrEPTcpUdpPriEntry
       MAX-ACCESS not-accessible
       STATUS current
       DESCRIPTION
               "An entry for mapping one specified TCP/UDP port number to
                one prioritized Queue in designated EP. "
       INDEX { eocBrEPTcpUdpEPIndex, eocBrEPTcpUdpRuleNum }         
       ::= { eocBrEPTcpUdpPriTable 1 }
       
EoCBrEPTcpUdpPriEntry ::= SEQUENCE {
               eocBrEPTcpUdpEPIndex Integer32,
               eocBrEPTcpUdpRuleNum Integer32,
               eocBrEPTcpUdpEPMac MacAddress,
               eocBrEPTcpUdpEnableCtrl INTEGER,
               eocBrEPTcpUdpPortNum INTEGER,
               eocBrEPTcpUdpMappedQueue INTEGER
--               eocBrEPTcpUdpRowStatus RowStatus
       }

-- 1,3,6,1,4,1,890,1,15,5,1,11,3,2,1,1
eocBrEPTcpUdpEPIndex OBJECT-TYPE
       SYNTAX Integer32
       MAX-ACCESS read-only
       STATUS current
       DESCRIPTION
               "Designate EP index. "
       ::= { eocBrEPTcpUdpPriEntry 1 }
                    
-- 1,3,6,1,4,1,890,1,15,5,1,11,3,2,1,2       
eocBrEPTcpUdpRuleNum OBJECT-TYPE
       SYNTAX Integer32
       MAX-ACCESS read-only
       STATUS current
       DESCRIPTION
               "TCP/UDP port number index. "
       ::= { eocBrEPTcpUdpPriEntry 2 }
       
-- 1,3,6,1,4,1,890,1,15,5,1,11,3,2,1,3
eocBrEPTcpUdpEPMac OBJECT-TYPE
       SYNTAX MacAddress
       MAX-ACCESS read-only
       STATUS current
       DESCRIPTION
               "The designated EP device Mac address. "
       ::= { eocBrEPTcpUdpPriEntry 3 }
              
-- 1,3,6,1,4,1,890,1,15,5,1,11,3,2,1,4
eocBrEPTcpUdpEnableCtrl OBJECT-TYPE
        SYNTAX INTEGER {
               disable(0),
               enable(1)
       }
       MAX-ACCESS read-write
       STATUS current
       DESCRIPTION
               "Enable TCP/UDP port priority or not. "
       ::= { eocBrEPTcpUdpPriEntry 4 } 
                    
-- 1,3,6,1,4,1,890,1,15,5,1,11,3,2,1,5
eocBrEPTcpUdpPortNum OBJECT-TYPE
       SYNTAX INTEGER (0..65535)
       MAX-ACCESS read-write
       STATUS current
       DESCRIPTION
               "Specify the TCP/UDP port number to be mapped. "
       ::= { eocBrEPTcpUdpPriEntry 5 }

-- 1,3,6,1,4,1,890,1,15,5,1,11,3,2,1,6
eocBrEPTcpUdpMappedQueue OBJECT-TYPE
       SYNTAX INTEGER {
               q0(0),
               q1(1),
               q2(2),
               q3(3)
       }
       MAX-ACCESS read-write
       STATUS current
       DESCRIPTION
               "Specify the mapped Queue for the TCP/UDP port number. "
       ::= { eocBrEPTcpUdpPriEntry 6 }
       
-- 1,3,6,1,4,1,890,1,15,5,1,11,3,2,1,7
-- eocBrEPTcpUdpRowStatus OBJECT-TYPE
--       SYNTAX RowStatus
--       MAX-ACCESS read-create
--       STATUS current
--       DESCRIPTION
--               "To create, delete or modify a TCP/UDP port number 
--                priority mapping entry(one row) in this table. "
--       ::= { eocBrEPTcpUdpPriEntry 7 }

-- ----------------------------------------------------------------------------
-- eocBrEPEtherGroup(11).eocBrEPEtherQoS(3)

-- 1,3,6,1,4,1,890,1,15,5,1,11,3,3
eocBrEPQueueSchTable OBJECT-TYPE       
       SYNTAX SEQUENCE OF EoCBrEPQueueSchEntry
       MAX-ACCESS not-accessible
       STATUS current
       DESCRIPTION
               "A table that maps priority queue scheduling mechanism in designated EP. "         
       ::= { eocBrEPEtherQoS 3}
       
eocBrEPQueueSchEntry OBJECT-TYPE
       SYNTAX EoCBrEPQueueSchEntry
       MAX-ACCESS not-accessible
       STATUS current
       DESCRIPTION
               "An entry that maps priority queue scheduling mechanism in designated EP. "
       INDEX { eocBrEPQueueSchEPIndex}         
       ::= { eocBrEPQueueSchTable 1 }
       
EoCBrEPQueueSchEntry ::= SEQUENCE {
               eocBrEPQueueSchEPIndex Integer32,
               eocBrEPQueueSchEPMac   MacAddress,
               eocBrEPQueueSchType    INTEGER
       }
       
-- 1,3,6,1,4,1,890,1,15,5,1,11,3,3,1,1
eocBrEPQueueSchEPIndex OBJECT-TYPE
       SYNTAX Integer32
       MAX-ACCESS read-only
       STATUS current
       DESCRIPTION
               "Designate EP index. "
       ::= { eocBrEPQueueSchEntry 1 }
       
-- 1,3,6,1,4,1,890,1,15,5,1,11,3,3,1,2
eocBrEPQueueSchEPMac OBJECT-TYPE
       SYNTAX MacAddress
       MAX-ACCESS read-only
       STATUS current
       DESCRIPTION
               "The designated EP device Mac address. "
       ::= { eocBrEPQueueSchEntry 2}       
                    
-- 1,3,6,1,4,1,890,1,15,5,1,11,3,3,1,3                     
eocBrEPQueueSchType OBJECT-TYPE
       SYNTAX INTEGER {
            strict(0), 
            wfq(1),
            mix(2)
       }
       MAX-ACCESS read-write
       STATUS current
       DESCRIPTION
                "The packets priority queue scheduling mechanism. There are 3 different
                 modes: 'Strict priority(SP)', 'Weighted fair queue(WFR)' and 'Mixed SP & WFR'.
                 SP: Packets residing in the higher priority queues transmit first. 
                     Lower priority packets transmit once these queues are emptied.
                     Highest priority Q3 goes first always, follows Q2 if Q3 is empty,
                     then Q1 and lowest Q0.
                 WFR:Each queue is assigned a service weight ratio that determines how many 
                     packets are sent from it. Weight is fixed at 8:4:2:1 for Q3:Q2:Q1:Q0.
                 MIX:Highest priority Q3 use SP, and other queues conform to WFR at 4:2:1 weight. "      
       ::= { eocBrEPQueueSchEntry 3 }
       
-- ----------------------------------------------------------------------------
-- eocBrEPEtherGroup(11).eocBrEPEtherQoS(4)

-- 1,3,6,1,4,1,890,1,15,5,1,11,3,4
eocBrEPPriSchemeTable OBJECT-TYPE       
       SYNTAX SEQUENCE OF EoCBrEPPriSchemeEntry
       MAX-ACCESS not-accessible
       STATUS current
       DESCRIPTION
               "A table of priority scheme in designated EP. "         
       ::= { eocBrEPEtherQoS 4}
       
eocBrEPPriSchemeEntry OBJECT-TYPE
       SYNTAX EoCBrEPPriSchemeEntry
       MAX-ACCESS not-accessible
       STATUS current
       DESCRIPTION
               "An entry of priority scheme in designated EP. "
       INDEX { eocBrEPPriSchemeEPIndex}         
       ::= { eocBrEPPriSchemeTable 1 }
       
EoCBrEPPriSchemeEntry ::= SEQUENCE {
               eocBrEPPriSchemeEPIndex Integer32,
               eocBrEPPriSchemeEPMac   MacAddress,
               eocBrEPPriSchemeSelect  INTEGER
       }
       
-- 1,3,6,1,4,1,890,1,15,5,1,11,3,3,1,1
eocBrEPPriSchemeEPIndex OBJECT-TYPE
       SYNTAX Integer32
       MAX-ACCESS read-only
       STATUS current
       DESCRIPTION
               "Designate EP index. "
       ::= { eocBrEPPriSchemeEntry 1 }
       
-- 1,3,6,1,4,1,890,1,15,5,1,11,3,3,1,2
eocBrEPPriSchemeEPMac OBJECT-TYPE
       SYNTAX MacAddress
       MAX-ACCESS read-only
       STATUS current
       DESCRIPTION
               "The designated EP device Mac address. "
       ::= { eocBrEPPriSchemeEntry 2}       
                    
-- 1,3,6,1,4,1,890,1,15,5,1,11,3,3,1,3                     
eocBrEPPriSchemeSelect OBJECT-TYPE
       SYNTAX INTEGER {
            use8021p(0), 
            useIP(1)
       }
       MAX-ACCESS read-write
       STATUS current
       DESCRIPTION
               "Setup which packet field for priority queue mapping.
                802.1p:Based on packet's 802.1p field for priority queue mapping. 
                       7/6 goes to Q3 (highest priority), 5/4 to Q2, 3/2 to Q1, 1/0 to Q0(lowest priority).
                IP:    Based on packet's IP TOS/TC or DSCP field for priority queue mapping.
                       The precedence 2 bits in this field (DSCP/TOS/TC) decide the destined priority queue (Q3/Q2/Q1/Q0).
                       b'11 goes to Q3, b'10 to Q2, b01 to Q1, and b'00 to Q0. "     
       ::= { eocBrEPPriSchemeEntry 3 } 
             
-- ----------------------------------------------------------------------------
-- 1,3,6,1,4,1,890,1,15,5,1,11,4
eocBrEPEtherIGMPSnoop OBJECT IDENTIFIER ::= { eocBrEPEtherGroup 4 }

-- 1,3,6,1,4,1,890,1,15,5,1,11,4,1  
eocBrEPIGMPSnoopTable OBJECT-TYPE
       SYNTAX SEQUENCE OF EoCBrEPIGMPSnoopEntry
       MAX-ACCESS not-accessible
       STATUS current
       DESCRIPTION
               "Table of designated EP Ethernet IGMP Snooping config. "
       ::= { eocBrEPEtherIGMPSnoop 1 }

eocBrEPIGMPSnoopEntry OBJECT-TYPE
       SYNTAX EoCBrEPIGMPSnoopEntry
       MAX-ACCESS not-accessible
       STATUS current
       DESCRIPTION
               "An entry in the designated EP Ethernet IGMP Snooping config table. "
       INDEX { eocBrEPIGMPSnoopEPIndex }
       ::= { eocBrEPIGMPSnoopTable 1 }

EoCBrEPIGMPSnoopEntry ::= SEQUENCE {
               eocBrEPIGMPSnoopEPIndex Integer32,
               eocBrEPIGMPSnoopEPMac MacAddress,
               eocBrEPIGMPSnoopEnableCtrl INTEGER
       }
       
-- 1,3,6,1,4,1,890,1,15,5,1,11,4,1,1,1
eocBrEPIGMPSnoopEPIndex OBJECT-TYPE
       SYNTAX Integer32
       MAX-ACCESS read-only
       STATUS current
       DESCRIPTION
               "Designate EP index. "
       ::= { eocBrEPIGMPSnoopEntry 1 }
              
-- 1,3,6,1,4,1,890,1,15,5,1,11,4,1,1,2
eocBrEPIGMPSnoopEPMac OBJECT-TYPE
       SYNTAX MacAddress
       MAX-ACCESS read-only
       STATUS current
       DESCRIPTION
               "The designated EP device Mac address. "
       ::= { eocBrEPIGMPSnoopEntry 2 }
              
-- 1,3,6,1,4,1,890,1,15,5,1,11,4,1,1,3
eocBrEPIGMPSnoopEnableCtrl OBJECT-TYPE
       SYNTAX INTEGER {
            disable(0), 
            enable(1)
       }
       MAX-ACCESS read-write
       STATUS current
       DESCRIPTION
               "Enable IGMP v1/v2 Snooping or not in EP. Not support IGMP v3 Snooping. "
       ::= { eocBrEPIGMPSnoopEntry 3 }

-- ----------------------------------------------------------------------------
-- 1,3,6,1,4,1,890,1,15,5,1,11,5
eocBrEPEtherTagVLAN OBJECT IDENTIFIER ::= { eocBrEPEtherGroup 5 }

-- 1,3,6,1,4,1,890,1,15,5,1,11,5,1  
eocBrEPTagVLANCtrlTable OBJECT-TYPE
       SYNTAX SEQUENCE OF EoCBrEPTagVLANCtrlEntry
       MAX-ACCESS not-accessible
       STATUS current
       DESCRIPTION
               "Table of designated EP Ethernet Tag VLAN enable control. "
       ::= { eocBrEPEtherTagVLAN 1 }

eocBrEPTagVLANCtrlEntry OBJECT-TYPE
       SYNTAX EoCBrEPTagVLANCtrlEntry
       MAX-ACCESS not-accessible
       STATUS current
       DESCRIPTION
               "An entry in the designated EP Ethernet Tag VLAN enable control table. "
       INDEX { eocBrEPTagVLANEPIndex }
       ::= { eocBrEPTagVLANCtrlTable 1 }

EoCBrEPTagVLANCtrlEntry ::= SEQUENCE {
               eocBrEPTagVLANEPIndex Integer32, 
               eocBrEPTagVLANEPMac MacAddress,
               eocBrEPTagVLANEnableCtrl INTEGER
       }
       
-- 1,3,6,1,4,1,890,1,15,5,1,11,5,1,1,1
eocBrEPTagVLANEPIndex OBJECT-TYPE
       SYNTAX Integer32
       MAX-ACCESS read-only
       STATUS current
       DESCRIPTION
               "Designate EP index. "
       ::= { eocBrEPTagVLANCtrlEntry 1 }
              
-- 1,3,6,1,4,1,890,1,15,5,1,11,5,1,1,2
eocBrEPTagVLANEPMac OBJECT-TYPE
       SYNTAX MacAddress
       MAX-ACCESS read-only
       STATUS current
       DESCRIPTION
               "The designated EP device Mac address. "
       ::= { eocBrEPTagVLANCtrlEntry 2 }
       
       
-- 1,3,6,1,4,1,890,1,15,5,1,11,5,1,1,3
eocBrEPTagVLANEnableCtrl OBJECT-TYPE
       SYNTAX INTEGER {
            disable(0),
            enable(1)
       }
       MAX-ACCESS read-write
       STATUS current
       DESCRIPTION
               "Enable EP Tagged VLAN(802.1Q) or not. "
       ::= { eocBrEPTagVLANCtrlEntry 3 }    

-- ----------------------------------------------------------------------------
-- 1,3,6,1,4,1,890,1,15,5,1,11,5,2
eocBrEPTagPortTable OBJECT-TYPE
       SYNTAX SEQUENCE OF EoCBrEPTagPortEntry
       MAX-ACCESS not-accessible
       STATUS current
       DESCRIPTION
               "Table of designated EP Ethernet Tagged VLAN(802.1Q) information. "
       ::= { eocBrEPEtherTagVLAN 2 }

eocBrEPTagPortEntry OBJECT-TYPE
       SYNTAX EoCBrEPTagPortEntry
       MAX-ACCESS not-accessible
       STATUS current
       DESCRIPTION
               "An entry in the designated EP Ethernet Tagged VLAN(802.1Q) table. "
       INDEX { eocBrEPTagPortEPIndex, eocBrEPTagPortPID }
       ::= { eocBrEPTagPortTable 1 }

EoCBrEPTagPortEntry ::= SEQUENCE {
               eocBrEPTagPortEPIndex Integer32,
               eocBrEPTagPortPID Integer32,
               eocBrEPTagPortEPMac MacAddress,               
               eocBrEPTagPortType INTEGER,
               eocBrEPTagPortPriority INTEGER,
               eocBrEPTagPortVID INTEGER,
               eocBrEPTagPortInRule INTEGER,
               eocBrEPTagPortOutRule INTEGER
       }
-- 1,3,6,1,4,1,890,1,15,5,1,11,5,2,1,1
eocBrEPTagPortEPIndex OBJECT-TYPE
       SYNTAX Integer32
       MAX-ACCESS read-only
       STATUS current
       DESCRIPTION
               "Designate EP index. "
       ::= { eocBrEPTagPortEntry 1 }
       
-- 1,3,6,1,4,1,890,1,15,5,1,11,5,2,1,2
eocBrEPTagPortPID OBJECT-TYPE
       SYNTAX Integer32
       MAX-ACCESS read-only
       STATUS current
       DESCRIPTION
               "EP port index. "
       ::= { eocBrEPTagPortEntry 2 }
              
-- 1,3,6,1,4,1,890,1,15,5,1,11,5,2,1,3
eocBrEPTagPortEPMac OBJECT-TYPE
       SYNTAX MacAddress
       MAX-ACCESS read-only
       STATUS current
       DESCRIPTION
               "The designated EP device Mac address. "
       ::= { eocBrEPTagPortEntry 3 }
       
-- 1,3,6,1,4,1,890,1,15,5,1,11,5,2,1,4
eocBrEPTagPortType OBJECT-TYPE
       SYNTAX INTEGER {
               ethernet(0),
               coax(1),
               phoneLine(2)
       }
       MAX-ACCESS read-only
       STATUS current
       DESCRIPTION
               "EP port type. "
       ::= { eocBrEPTagPortEntry 4 }
       
-- 1,3,6,1,4,1,890,1,15,5,1,11,5,2,1,5
eocBrEPTagPortPriority OBJECT-TYPE
       SYNTAX INTEGER (0..7)
       ACCESS read-write
       STATUS current
       DESCRIPTION
               "The default 802.1p priority value of current EP port. "
       ::= { eocBrEPTagPortEntry 5 }  
            
-- 1,3,6,1,4,1,890,1,15,5,1,11,5,2,1,6
eocBrEPTagPortVID OBJECT-TYPE
       SYNTAX INTEGER (1..4095)
       ACCESS read-write
       STATUS current
       DESCRIPTION
               "The default VLAN ID (VID) of current EP port. "
       ::= { eocBrEPTagPortEntry 6 }

-- 1,3,6,1,4,1,890,1,15,5,1,11,5,2,1,7
eocBrEPTagPortInRule OBJECT-TYPE
       SYNTAX INTEGER {
           all(0),
           tag(1)
       }
       ACCESS read-write
       STATUS current
       DESCRIPTION
               "Defines the 'action' (ingress rule) on packet enters current EP port. 
                all(0)->accept all(untagged/tagged) pkt and tag the untagged pkt.
                tag(1)->accept tagged pkt only. "
       ::= { eocBrEPTagPortEntry 7 }

-- 1,3,6,1,4,1,890,1,15,5,1,11,5,2,1,8
eocBrEPTagPortOutRule OBJECT-TYPE
       SYNTAX INTEGER {
           untag(0),
           tag(1),
           bypass(2)
       }
       ACCESS read-write
       STATUS current
       DESCRIPTION
               "Defines the 'action' (egress rule) on packet output from current EP port.
                untag(0)-> remove tag from tagged pkt. 
                tag(1)-> tag all output pkt.
                bypass(2)-> pass through either tagged or untagged pkt. "
       ::= { eocBrEPTagPortEntry 8 }

       
-- ----------------------------------------------------------------------------
-- 1,3,6,1,4,1,890,1,15,5,1,11,6
eocBrEPCtrl OBJECT IDENTIFIER ::= { eocBrEPEtherGroup 6 }

-- 1,3,6,1,4,1,890,1,15,5,1,11,6,1  
eocBrEPCtrlTable OBJECT-TYPE
       SYNTAX SEQUENCE OF EoCBrEPCtrlEntry
       MAX-ACCESS not-accessible
       STATUS current
       DESCRIPTION
               "Table of designated EP 'Ethernet default configuration operation' or 
                'reboot operation'. "
       ::= { eocBrEPCtrl 1 }

eocBrEPCtrlEntry OBJECT-TYPE
       SYNTAX EoCBrEPCtrlEntry
       MAX-ACCESS not-accessible
       STATUS current
       DESCRIPTION
               "An entry in the designated EP control table. "
       INDEX { eocBrEPCtrlEPIndex }
       ::= { eocBrEPCtrlTable 1 }

EoCBrEPCtrlEntry ::= SEQUENCE {
               eocBrEPCtrlEPIndex Integer32,
               eocBrEPCtrlEPMac MacAddress,
               eocBrEPCtrlEtherDefault INTEGER,
               eocBrEPCtrlReboot INTEGER
       }
       
-- 1,3,6,1,4,1,890,1,15,5,1,11,6,1,1,1
eocBrEPCtrlEPIndex OBJECT-TYPE
       SYNTAX Integer32
       MAX-ACCESS read-only
       STATUS current
       DESCRIPTION
               "Designate EP index. "
       ::= { eocBrEPCtrlEntry 1 }
              
-- 1,3,6,1,4,1,890,1,15,5,1,11,6,1,1,2
eocBrEPCtrlEPMac OBJECT-TYPE
       SYNTAX MacAddress
       MAX-ACCESS read-only
       STATUS current
       DESCRIPTION
               "The designated EP device Mac address. "
       ::= { eocBrEPCtrlEntry 2}

-- 1,3,6,1,4,1,890,1,15,5,1,11,6,1,1,3
eocBrEPCtrlEtherDefault OBJECT-TYPE
       SYNTAX INTEGER {
            idle(0), 
            activate(1)
       }
       MAX-ACCESS read-write
       STATUS current
       DESCRIPTION
               "To reset designated EP Ethernet configuration to factory default, 
                the SNMP manager need to set the value to activate(1); and submit to 
                the bridge to reset destined designated EP configuration. 
                The value will back to idle(0)once completed. "
       ::= { eocBrEPCtrlEntry 3 }
     
-- 1,3,6,1,4,1,890,1,15,5,1,11,6,1,1,4
eocBrEPCtrlReboot OBJECT-TYPE
       SYNTAX INTEGER {
            idle(0), 
            activateThenReboot(1)
       }
       MAX-ACCESS read-write
       STATUS current
       DESCRIPTION
               "To reboot designated EP, the SNMP manager need to 
                set the value to activateThenReboot(1); and submit to the bridge 
                to reboot destined designated EP. 
                The value will back to idle(0) once completed. "
       ::= { eocBrEPCtrlEntry 4 }

-- ----------------------------------------------------------------------------
-- 1,3,6,1,4,1,890,1,15,5,1,11,7
eocBrEPHostMacFilter OBJECT IDENTIFIER  ::= { eocBrEPEtherGroup 7 }

-- 1,3,6,1,4,1,890,1,15,5,1,11,7,1
eocBrEPHostMacFilterTable OBJECT-TYPE       
       SYNTAX SEQUENCE OF EoCBrEPHostMacFilterEntry
       MAX-ACCESS not-accessible
       STATUS current
       DESCRIPTION
               "Table of allowable host Mac(s) in designated EP. "         
       ::= { eocBrEPHostMacFilter 1}
           
eocBrEPHostMacFilterEntry OBJECT-TYPE
       SYNTAX EoCBrEPHostMacFilterEntry
       MAX-ACCESS not-accessible
       STATUS current
       DESCRIPTION
               "An entry for allowable host Mac in designated EP. "
       INDEX { eocBrEPHostMacFilterEPIndex, eocBrEPHostMacFilterSetNum }         
       ::= { eocBrEPHostMacFilterTable 1 }
       
EoCBrEPHostMacFilterEntry ::= SEQUENCE {
               eocBrEPHostMacFilterEPIndex Integer32,
               eocBrEPHostMacFilterSetNum Integer32,
               eocBrEPHostMacFilterEPMac MacAddress,
               eocBrEPHostMacFilterEnableCtrl INTEGER,
               eocBrEPHostMacFilterHostMac MacAddress
--               eocBrEPHostMacFilterRowStatus RowStatus
       }

-- 1,3,6,1,4,1,890,1,15,5,1,11,7,1,1,1
eocBrEPHostMacFilterEPIndex OBJECT-TYPE
       SYNTAX Integer32
       MAX-ACCESS read-only
       STATUS current
       DESCRIPTION
               "Designate EP index. "
       ::= { eocBrEPHostMacFilterEntry 1 }
                    
-- 1,3,6,1,4,1,890,1,15,5,1,11,7,1,1,2       
eocBrEPHostMacFilterSetNum OBJECT-TYPE
       SYNTAX Integer32
       MAX-ACCESS read-only
       STATUS current
       DESCRIPTION
               "Mac filter set index. "
       ::= { eocBrEPHostMacFilterEntry 2 }
       
-- 1,3,6,1,4,1,890,1,15,5,1,11,7,1,1,3
eocBrEPHostMacFilterEPMac OBJECT-TYPE
       SYNTAX MacAddress
       MAX-ACCESS read-only
       STATUS current
       DESCRIPTION
               "The designated EP device Mac address. "
       ::= { eocBrEPHostMacFilterEntry 3 }
              
-- 1,3,6,1,4,1,890,1,15,5,1,11,7,1,1,4
eocBrEPHostMacFilterEnableCtrl OBJECT-TYPE
        SYNTAX INTEGER {
               disable(0),
               enable(1)
       }
       MAX-ACCESS read-only
       STATUS current
       DESCRIPTION
               "Tell current host Mac filter set status -- enable(not null MAC) or disable(null MAC).
                Host Mac filter function will be off if none Mac filter set exists. "
       ::= { eocBrEPHostMacFilterEntry 4 } 
                    
-- 1,3,6,1,4,1,890,1,15,5,1,11,7,1,1,5
eocBrEPHostMacFilterHostMac OBJECT-TYPE
       SYNTAX MacAddress
       MAX-ACCESS read-write
       STATUS current
       DESCRIPTION
               "Specify the allowable host Mac. Set to null MAC(00-00-00-00-00-00) to disable current entry.
                Host Mac filter function will be off if none Mac filter set exists. "
       ::= { eocBrEPHostMacFilterEntry 5 }


                            
-- EoC=====================================================================
-- TRAP
--
-- snmpBasicNotificationsGroup NOTIFICATION-GROUP
--        NOTIFICATIONS { coldStart, authenticationFailure }
--        STATUS current
--        DESCRIPTION
--               "The two notifications which an SNMPv2 entity is required to implement."
--        ::= { snmpMIBGroups 7 } 

eocBrHttpLoginNotification NOTIFICATION-TYPE
        OBJECTS {
            eocBrAccountName
        }
        STATUS current
        --&ACTIONS { log, normal, clrdups }
        --&MESG "User $'1, login by HTTP. "
        DESCRIPTION
                 "A user login to the Master by HTTP. "
       ::= { eoc350BrNotification 1 }

eocBrHttpLogoutNotification NOTIFICATION-TYPE
        OBJECTS {
            eocBrAccountName
        }
        STATUS current
        --&ACTIONS { log, normal, clrdups }
        --&MESG "User $'1, logout by HTTP. "     
        DESCRIPTION
                 "A user logout to Master by HTTP. "
       ::= { eoc350BrNotification 2 }

eocBrHttpLoginAuthFailedNotification NOTIFICATION-TYPE
        OBJECTS {
            eocBrAccountName
        }
        STATUS current
        --&ACTIONS { log, warning, clrdups }
        --&MESG "User $'1, login by HTTP, failed. "       
        DESCRIPTION
                 "A failed login by HTTP with invalid username/password. "
       ::= { eoc350BrNotification 3}
       
eocBrTelnetLoginNotification NOTIFICATION-TYPE
        OBJECTS {
            eocBrAccountName
        }
        STATUS current
        --&ACTIONS { log, normal, clrdups }
        --&MESG "User $'1, login by TELNET. "    
        DESCRIPTION
                 "A user login to the Master by TELNET. "
       ::= { eoc350BrNotification 4 }

eocBrTelnetLogoutNotification NOTIFICATION-TYPE
        OBJECTS {
            eocBrAccountName
        }
        STATUS current
        --&ACTIONS { log, normal, clrdups }
        --&MESG "User $'1, logout by TELNET. "   
        DESCRIPTION
                 "A user logout to Master by TELNET. "
       ::= { eoc350BrNotification 5 }

eocBrTelnetLoginAuthFailedNotification NOTIFICATION-TYPE
        OBJECTS {
            eocBrAccountName
        }
        STATUS current
        --&ACTIONS { log, warning, clrdups }
        --&MESG "User $'1, login by TELNET, failed. "     
        DESCRIPTION
                 "A failed login by TELNET with invalid username/password. "
       ::= { eoc350BrNotification 6 }
       
eocBrSystemFwUpgradeNotification NOTIFICATION-TYPE
        OBJECTS {
            eocBrSystemFwWorkingVersion,
            eocBrSystemFwUploadVersion
        }
        STATUS current
        --&ACTIONS { log, major, clrdups }
        --&MESG "Upgrade system firmware from version $'1 to $'2, and reboot. "       
        DESCRIPTION
             "Upgrade system firmware. "
        ::= { eoc350BrNotification 11 } 
               
eocBrDhcpClientAckNotification NOTIFICATION-TYPE
        OBJECTS {
            eocBrSystemMac,
            eocBrIPAddress,
            eocBrDHCPLease,
            eocBrIPAddress
        }
        STATUS current
        --&ACTIONS { log, major, clrdups }
        --&MESG "Ack to system DHCP client, Master Ethernet MAC:$1 get IP:$2 with lease $3 seconds from DHCP server IP:$4 "       
        DESCRIPTION
             "Master gets IP by DHCP client. "
        ::= { eoc350BrNotification 21 }
        
eocBrHostDhcpClientAckNotification NOTIFICATION-TYPE
        OBJECTS {
            eocBrHostDHCPEPMac,
            eocBrHostDHCPHostMac,
            eocBrHostDHCPIPAddress,
            eocBrHostDHCPLease
        }
        STATUS current
        --&ACTIONS { log, info, clrdups }
        --&MESG "Ack to host DHCP client, host MAC:$2 @ EP:$1 get IP:$3 with lease $4 seconds "       
        DESCRIPTION
             "Host@EP gets IP via DHCP. "
        ::= { eoc350BrNotification 23 }
                        
eocBrAutoConfigTFTPGetOkNotification NOTIFICATION-TYPE
        OBJECTS {
            eocBrTFTPServerIPAddress,
            eocBrTFTPFilename
        }
        STATUS current
        --&ACTIONS { log, info, clrdups }
        --&MESG "Auto-Config, Master get file $'2 from TFTP server IP:$1, success. "         
        DESCRIPTION
             "Upload file to Master by TFTP for Auto Configuration, success. "
        ::= { eoc350BrNotification 27 }
        
eocBrAutoConfigTFTPGetErrorNotification NOTIFICATION-TYPE
        OBJECTS {
            eocBrTFTPServerIPAddress,
            eocBrTFTPFilename
        }
        STATUS current
        --&ACTIONS { log, info, clrdups }
        --&MESG "Auto-Config, Master get/parse file $'2 from TFTP server IP:$1, failed. "         
        DESCRIPTION
             "Upload/Parse file error to Master by TFTP for Auto Configuration. "
        ::= { eoc350BrNotification 28 }        
        
eocBrMasterDrvUpgradeNotification NOTIFICATION-TYPE
        OBJECTS {
            eocBrMasterMac,
            eocBrMasterDrvWorkingVersion,
            eocBrMasterDrvUploadVersion
        }
        STATUS current
        --&ACTIONS { log, major, clrdups }
        --&MESG "Upgrade EoC Master MAC:$1 driver from version $'2 to $'3 "        
        DESCRIPTION
             "Upgrade EoC Master driver. "
        ::= { eoc350BrNotification 71 }
          
eocBrEPDrvUpgradeNotification NOTIFICATION-TYPE
        OBJECTS {
            eocBrEPMac,
            eocBrEPDrvWorkingVersion,
            eocBrEPDrvUploadVersion
        }
        STATUS current
        --&ACTIONS { log, major, clrdups }
        --&MESG "Upgrade EP:$1 driver from version $'2 to $'3 "    
        DESCRIPTION
             "Upgrade EoC EP driver. "
        ::= { eoc350BrNotification 81 }
                     
eocBrEPOnlineStatusNotification NOTIFICATION-TYPE
        OBJECTS {
            eocBrEPMac,
            eocBrEPOnlineStatus,
            eocBrSystemMac
        }
        STATUS current
        --&ACTIONS { log, info, clrdups }
        --&MESG "EP:$1 @ Master Ethernet MAC:$3, online status $2 "    
        DESCRIPTION
             "EP on-line status changed. "
        ::= { eoc350BrNotification 82 }
        
eocBrEPDiagResultNotification NOTIFICATION-TYPE
        OBJECTS {
            eocBrEPMac,
            eocBrEPDiagDnLinkResult,
            eocBrEPDiagUpLinkResult
        }
        STATUS current
        --&ACTIONS { log, info, clrdups } 
        --&MESG "Diagnosis result of EP:$1 => DnLink(Tx) to EP:$'2, UpLink(Rx) from EP:$'3 "    
        DESCRIPTION
             "EP diagnosis report. "
        ::= { eoc350BrNotification 83 }        
        
eocBrTFTPGetOkNotification NOTIFICATION-TYPE
        OBJECTS {
            eocBrTFTPServerIPAddress,
            eocBrTFTPFilename
        }
        STATUS current
        --&ACTIONS { log, info, clrdups }
        --&MESG "Master get file $'2 from TFTP server IP:$1, success. "         
        DESCRIPTION
             "Upload file to Master by TFTP, success. "
        ::= { eoc350BrNotification 91 }
        
eocBrTFTPGetErrorNotification NOTIFICATION-TYPE
        OBJECTS {
            eocBrTFTPServerIPAddress,
            eocBrTFTPFilename
        }
        STATUS current
        --&ACTIONS { log, info, clrdups }
        --&MESG "Master get file $'2 from TFTP server IP:$1, checksum error, failed. "         
        DESCRIPTION
             "Upload file to Master by TFTP, failed. "
        ::= { eoc350BrNotification 92 }        
        
eocBrHTTPGetNotification NOTIFICATION-TYPE
        OBJECTS {
            eocBrTFTPServerIPAddress
        }
        STATUS current
        --&ACTIONS { log, info, clrdups }
        --&MESG "Upload file from IP:$1 onto Master by HTTP, success. "     
        DESCRIPTION
             "Upload file to Master by HTTP. "
        ::= { eoc350BrNotification 51 }        
                      
END
