-- ZyXEL Communications Corporation
-- Private Enterprise MIB definition 
  
-- This file describes the ZyXEL Communications Corporation Enterprise MIB.
-- It contains ZyXEL products OIDs, and common managed objects.

-- $Log: ZYXEL-QUEUING-METHOD-MIB.mib $ 
-- Revision 1.4  2012/09/19 07:45:25  Kevin 
-- if it's leaf node, revise the vender name from zyxel to zy 
-- Revision 1.3  2012/08/22 09:47:54  Kevin 
-- clean warning for SNMPc 
-- Revision 1.2  2012/07/05 06:24:28  Kevin 
-- 1. upgrade from SNMP to SNMPv2  
-- 2. clean warning 
-- Revision 1.1  2012/05/30 07:50:28  Kevin 
-- Initial revision 

ZYXEL-QUEUING-METHOD-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelQueuingMethod MODULE-IDENTITY
		LAST-UPDATED	"201207010000Z"    
		ORGANIZATION "Enterprise Solution ZyXEL"     
		CONTACT-INFO
			""	   
		DESCRIPTION
			"The subtree for queuing method"
		::= { esMgmt 70 }
		
	zyxelQueuingMethodSetup OBJECT IDENTIFIER ::= { zyxelQueuingMethod 1 }
	                                                                      
	  
-- *******************************************************************
-- *
-- * zyxelQueuingMethodSetup
-- *
-- *******************************************************************

--  zyxelQueuingMethodPortTable
        zyxelQueuingMethodPortTable OBJECT-TYPE
        SYNTAX	SEQUENCE OF ZyxelQueuingMethodPortEntry
        MAX-ACCESS  not-accessible
        STATUS  current
        DESCRIPTION
                 	"The table contains queuing method outgoing port configuration. "
        ::= { zyxelQueuingMethodSetup 1 }
        
		zyxelQueuingMethodPortEntry OBJECT-TYPE
        SYNTAX	ZyxelQueuingMethodPortEntry
        MAX-ACCESS	not-accessible
        STATUS	current
        DESCRIPTION    	
					"An entry contains queuing method outgoing port configuration."
        INDEX          	{ dot1dBasePort, zyQueuingMethodPortQueue }
        ::= {zyxelQueuingMethodPortTable 1}

        ZyxelQueuingMethodPortEntry ::=
           SEQUENCE {
        	zyQueuingMethodPortQueue	INTEGER,
        	zyQueuingMethodPortWeight	INTEGER,
        	zyQueuingMethodPortMode		INTEGER
           }

        zyQueuingMethodPortQueue OBJECT-TYPE
        SYNTAX  INTEGER
        MAX-ACCESS  not-accessible
        STATUS  current
        DESCRIPTION
			"Number of queue(0...7) for the specified port."
        ::= { zyxelQueuingMethodPortEntry 1 }

        zyQueuingMethodPortWeight OBJECT-TYPE
        SYNTAX  INTEGER
        MAX-ACCESS  read-write
        STATUS  current
        DESCRIPTION
			"Set weight (0...15) of Queue. Bandwidth is divided across the different traffic queues according to 
			their weights. Queue with larger weight get more service than queues with smaller weights. "
        ::= { zyxelQueuingMethodPortEntry 2 }
 
        zyQueuingMethodPortMode OBJECT-TYPE
        SYNTAX  INTEGER {
        	strictly-priority(0),
        	weighted-fair-scheduling(1),
        	weighted-round-robin(2)
        }
        MAX-ACCESS  read-write
        STATUS  current
        DESCRIPTION
			"Select SPQ(Strictly Priority Queuing), WFQ(Weighted Fair Queuing), or WRR (Weighted Round Robin) 
			for the specified port."
        ::= { zyxelQueuingMethodPortEntry 3 }

-- zyxelQueuingMethodHybridSpqPortTable
        zyxelQueuingMethodHybridSpqPortTable OBJECT-TYPE
        SYNTAX	SEQUENCE OF	ZyxelQueuingMethodHybridSpqPortEntry
        MAX-ACCESS  not-accessible
        STATUS  current
        DESCRIPTION
                 	"The table contains queuing method hybird-SPQ outgoing port configuration. "
        ::= { zyxelQueuingMethodSetup 2 }
        
		zyxelQueuingMethodHybridSpqPortEntry OBJECT-TYPE
        SYNTAX	ZyxelQueuingMethodHybridSpqPortEntry
        MAX-ACCESS	not-accessible
        STATUS	current
        DESCRIPTION    	
					"An entry contains queuing method hybird-SPQ outgoing port configuration."
        INDEX          	{ dot1dBasePort }
        ::= { zyxelQueuingMethodHybridSpqPortTable 1 }

        ZyxelQueuingMethodHybridSpqPortEntry ::=
           SEQUENCE {
        		zyQueuingMethodHybridSpqPortQueue	INTEGER
           }    
                  
        zyQueuingMethodHybridSpqPortQueue	OBJECT-TYPE
        SYNTAX  INTEGER {
        	none(0),
        	q0(1),
        	q1(2),
        	q2(3),
        	q3(4),
        	q4(5),
        	q5(6),
        	q6(7),
        	q7(8)
        }
        MAX-ACCESS  read-write
        STATUS  current
        DESCRIPTION
			"This is applicable only when you select WFQ or WRR. Select a queue to have the switch use SPQ to 
			service the subsequent queue after and including the specified queue.This is applicable only when  
			you select WFQ or WRR."
        ::= { zyxelQueuingMethodHybridSpqPortEntry 1 }

END
