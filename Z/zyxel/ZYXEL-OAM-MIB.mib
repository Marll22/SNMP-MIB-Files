-- ZyXEL Communications Corporation
-- Private Enterprise MIB definition 
  
-- This file describes the ZyXEL Communications Corporation Enterprise MIB.
-- It contains ZyXEL products OIDs, and common managed objects.

-- $Log: ZYXEL-OAM-MIB.mib $ 
-- Revision 1.4  2013/12/10 07:17:40  ccho 
-- remove uncessary imports 
-- Revision 1.3  2012/09/19 07:42:55  Kevin 
-- if it's leaf node, revise the vender name from zyxel to zy 
-- Revision 1.2  2012/07/05 06:24:04  Kevin 
-- 1. upgrade from SNMP to SNMPv2  
-- 2. clean warning 
-- Revision 1.1  2012/05/30 07:50:21  Kevin 
-- Initial revision 

ZYXEL-OAM-MIB DEFINITIONS ::= BEGIN

    IMPORTS
	OBJECT-TYPE
		FROM SNMPv2-SMI			-- RFC2578	
		
	MODULE-IDENTITY
		FROM SNMPv2-SMI
	DisplayString FROM SNMPv2-TC
	
	EnabledStatus
		FROM  P-BRIDGE-MIB

    ifIndex
    	FROM IF-MIB					-- RFC2863

	esMgmt			
		FROM ZYXEL-ES-SMI;

	zyxelOam MODULE-IDENTITY
		LAST-UPDATED	"201207010000Z"    
		ORGANIZATION "Enterprise Solution ZyXEL"     
		CONTACT-INFO
			""	   
		DESCRIPTION
			"The subtree for Operations, Administration, and Maintenance (OAM) and 
			OAM Unidirectional Link Detection (OULD)."
		::= { esMgmt 56 }

	zyxelOamSetup     		OBJECT IDENTIFIER ::= { zyxelOam 1 }
	zyxelOamOuldSetup 		    OBJECT IDENTIFIER ::= { zyxelOam 2 }
	zyxelOamOuldStatus          OBJECT IDENTIFIER ::= { zyxelOam 3 }

-- zyxelOamSetup    
        zyOamState OBJECT-TYPE
        SYNTAX  EnabledStatus
        MAX-ACCESS  read-write
        STATUS  current
        DESCRIPTION
 			"Enable/disable administrative status on the switch."
        ::= { zyxelOamSetup 1 }

        zyxelOamPortTable OBJECT-TYPE
        SYNTAX	SEQUENCE OF ZyxelOamPortEntry
        MAX-ACCESS  not-accessible
        STATUS  current
        DESCRIPTION
            "The table contains OAM (Operations, Administration, and Maintenance) configurations for all ports."
        ::= { zyxelOamSetup 2 }
        
		zyxelOamPortEntry OBJECT-TYPE
        SYNTAX	ZyxelOamPortEntry
        MAX-ACCESS	not-accessible
        STATUS	current
        DESCRIPTION    	
            "An entry contains OAM configurations for a specific port."
        INDEX          	{ ifIndex }
        ::= { zyxelOamPortTable 1 }

        ZyxelOamPortEntry ::=
           SEQUENCE {
                zyOamPortState                  EnabledStatus,
	       zyOamPortFunctionsSupported          BITS
           }

    zyOamPortState OBJECT-TYPE
        SYNTAX  EnabledStatus
        MAX-ACCESS  read-write
        STATUS  current
        DESCRIPTION
            "Enable/disable OAM status on a specific port."
        ::= { zyxelOamPortEntry 1 }
        
        zyOamPortFunctionsSupported OBJECT-TYPE
        SYNTAX      BITS {
                      unidirectionalSupport (0),
                      loopbackSupport(1),
                      eventSupport(2),
                      variableSupport(3)
                    }
        MAX-ACCESS  read-write
        STATUS	current
        DESCRIPTION
          "The OAM functions supported on this Ethernet-like interface. OAM consists of separate functional sets beyond 
          the basic discovery process that is always required.  These functional groups can be supported independently by 
          any implementation. These values are communicated to the peer via the local configuration field of Information 
          OAMPDUs.
			Setting 'unidirectionalSupport(0)' indicates that the OA entity supports the transmission of OAMPDUs on links 
			that are operating in unidirectional mode (traffic flowing in one direction only).  
			Setting 'loopbackSupport(1)' indicates that the OAM entity can initiate and respond to loopback commands. 
			Setting 'eventSupport(2)' indicates that the OAM entity can send and receive Event Notification OAMPDUs.  
			Setting 'variableSupport(3)' indicates that the OAM entity can send and receive Variable Request and Response 
            OAMPDUs."
        REFERENCE   "[802.3ah], 30.3.6.1.6"
        ::= { zyxelOamPortEntry 2 }

-- zyxelOamOuldSetup
    zyOamOuldDiscoveryTimer OBJECT-TYPE
        SYNTAX  INTEGER (1..600)
        MAX-ACCESS  read-write
        STATUS  current
        DESCRIPTION
            "Set the value of OAM Unidirectional Link Detection (OULD discovery timer (second)."
        ::= { zyxelOamOuldSetup 1 } 

    zyOamOuldRecoveryTimer OBJECT-TYPE
        SYNTAX  INTEGER (10..600)
        MAX-ACCESS  read-write
        STATUS  current
        DESCRIPTION
            "Set the value of OAM Unidirectional Link Detection (OULD recovery timer (second)."
        ::= { zyxelOamOuldSetup 2 }

    zyxelOamOuldSetupPortTable OBJECT-TYPE
        SYNTAX	SEQUENCE OF ZyxelOamOuldSetupPortEntry
        MAX-ACCESS  not-accessible
        STATUS  current
        DESCRIPTION
            "The table contains OAM Unidirectional Link Detection (OULD) configurations for all ports."
        ::= { zyxelOamOuldSetup 3 }
        
    zyxelOamOuldSetupPortEntry OBJECT-TYPE
        SYNTAX	ZyxelOamOuldSetupPortEntry
        MAX-ACCESS	not-accessible
        STATUS	current
        DESCRIPTION    	
            "An entry contains OAM Unidirectional Link Detection (OULD) configurations for a specific port."
        INDEX          	{ ifIndex }
        ::= { zyxelOamOuldSetupPortTable 1 }

        ZyxelOamOuldSetupPortEntry ::=
        SEQUENCE {
            zyOamOuldState             EnabledStatus,
            zyOamOuldAggressiveMode    EnabledStatus            
        }
 
    zyOamOuldState OBJECT-TYPE
        SYNTAX  EnabledStatus
        MAX-ACCESS  read-write
        STATUS  current
        DESCRIPTION
            "Enable/disable OAM Unidirectional Link Detection (OULD) status on a specific port."
        ::= { zyxelOamOuldSetupPortEntry 1 }
        
    zyOamOuldAggressiveMode OBJECT-TYPE
        SYNTAX  EnabledStatus
        MAX-ACCESS  read-write
        STATUS  current
        DESCRIPTION
            "Enable/disable OAM Unidirectional Link Detection (OULD) aggression mode on a specific port."
        ::= { zyxelOamOuldSetupPortEntry 2 }    
        
-- zyxelOamOuldStatus    
    zyxelOamOuldStatusPortTable OBJECT-TYPE
        SYNTAX	SEQUENCE OF ZyxelOamOuldStatusPortEntry
        MAX-ACCESS  not-accessible
        STATUS  current
        DESCRIPTION
            "The table contains OAM Unidirectional Link Detection (OULD) status for all ports."
        ::= { zyxelOamOuldStatus 1 }
        
    zyxelOamOuldStatusPortEntry OBJECT-TYPE
        SYNTAX	ZyxelOamOuldStatusPortEntry
        MAX-ACCESS	not-accessible
        STATUS	current
        DESCRIPTION    	
            "An entry contains OAM Unidirectional Link Detection (OULD) status for a specific port."
        INDEX          	{ ifIndex }
        ::= { zyxelOamOuldStatusPortTable 1 }

        ZyxelOamOuldStatusPortEntry ::=
        SEQUENCE {            
            zyOamOuldResult            DisplayString,  
            zyOamOuldLinkStatus        DisplayString,         
            zyOamOuldCountdown         DisplayString    
        }
         
    zyOamOuldResult OBJECT-TYPE
        SYNTAX  DisplayString
        MAX-ACCESS  read-only
        STATUS  current
        DESCRIPTION
            "The result of OAM Unidirectional Link Detection (OULD) on a specific port."
        ::= { zyxelOamOuldStatusPortEntry 1 }   

    zyOamOuldLinkStatus OBJECT-TYPE
        SYNTAX  DisplayString
        MAX-ACCESS  read-only
        STATUS  current
        DESCRIPTION
            "Link status on a specific port."
        ::= { zyxelOamOuldStatusPortEntry 2 }   
        
    zyOamOuldCountdown OBJECT-TYPE
        SYNTAX  DisplayString
        MAX-ACCESS  read-only
        STATUS  current
        DESCRIPTION
            "The countdown of discovery or recovery time (second) on a specific port."
        ::= { zyxelOamOuldStatusPortEntry 3 }     
END
