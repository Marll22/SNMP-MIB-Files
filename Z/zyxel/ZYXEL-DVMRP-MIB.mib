-- ZyXEL Communications Corporation
-- Private Enterprise MIB definition 
  
-- This file describes the ZyXEL Communications Corporation Enterprise MIB.
-- It contains ZyXEL products OIDs, and common managed objects.

-- $Log: ZYXEL-DVMRP-MIB.mib $ 
-- Revision 1.3  2012/09/19 07:32:19  Kevin 
-- if it's leaf node, revise the vender name from zyxel to zy 
-- Revision 1.2  2012/07/05 06:22:38  Kevin 
-- 1. upgrade from SNMP to SNMPv2  
-- 2. clean warning 
-- Revision 1.1  2012/05/30 07:48:47  Kevin 
-- Initial revision 

ZYXEL-DVMRP-MIB DEFINITIONS ::= BEGIN

    IMPORTS
	enterprises		FROM RFC1155-SMI                                
	
	OBJECT-TYPE
		FROM SNMPv2-SMI			-- RFC2578	
	RowStatus, DateAndTime, TruthValue, StorageType, MacAddress ,TDomain, TAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	zyRouteDomainIpAddress, zyRouteDomainIpMaskBits
		FROM ZYXEL-IP-FORWARD-MIB
	esMgmt			
		FROM ZYXEL-ES-SMI;

	zyxelDvmrp MODULE-IDENTITY
		LAST-UPDATED	"201207010000Z"    
		ORGANIZATION "Enterprise Solution ZyXEL"     
		CONTACT-INFO
			""	   
		DESCRIPTION
			"The subtree for Distance Vector Multicast Routing Protocol (DVMRP)"
		::= { esMgmt 23 }
		
	zyxelDvmrpSetup     			OBJECT IDENTIFIER ::= { zyxelDvmrp 1 }		

        zyDvmrpState OBJECT-TYPE
        SYNTAX  EnabledStatus
        MAX-ACCESS  read-write
        STATUS  current
        DESCRIPTION
        "Enable/Disable DVMRP on the switch."
        ::= { zyxelDvmrpSetup 1 }
        
        zyDvmrpThreshold OBJECT-TYPE
        SYNTAX  INTEGER
        MAX-ACCESS  read-write
        STATUS  current
        DESCRIPTION
        "The maximum time to live value. This applies only to multicast traffic this switch sends out."
        ::= { zyxelDvmrpSetup 2 }        
        
		zyxelDvmrpRouteDomainTable OBJECT-TYPE
        SYNTAX	SEQUENCE OF ZyxelDvmrpRouteDomainEntry
        MAX-ACCESS  not-accessible
        STATUS  current
        DESCRIPTION
        "The table contains DVMRP configuration."
        ::= { zyxelDvmrpSetup 3 }
        
		zyxelDvmrpRouteDomainEntry OBJECT-TYPE
        SYNTAX	ZyxelDvmrpRouteDomainEntry
        MAX-ACCESS	not-accessible
        STATUS	current
        DESCRIPTION    	
		"An entry contains DVMRP configuration."
        INDEX          	{ zyRouteDomainIpAddress, zyRouteDomainIpMaskBits }
        ::= { zyxelDvmrpRouteDomainTable 1 }

        ZyxelDvmrpRouteDomainEntry ::=
           SEQUENCE {
        	zyDvmrpRouteDomainState		EnabledStatus
           }
                   
        zyDvmrpRouteDomainState OBJECT-TYPE
        SYNTAX  EnabledStatus
        MAX-ACCESS  read-write
        STATUS  current
        DESCRIPTION
        "Enable/Disable DVMRP on this IP routing domain."
        ::= { zyxelDvmrpRouteDomainEntry 1 }

END
