-- ZyXEL Communications Corporation
-- Private Enterprise MIB definition 
  
-- This file describes the ZyXEL Communications Corporation Enterprise MIB.
-- It contains ZyXEL products OIDs, and common managed objects.

-- $Log: ZYXEL-GREEN-ETHERNET-MIB.mib $ 
-- Revision 1.2  2012/09/19 07:34:58  Kevin 
-- 1. if it's leaf node, revise the vender name from zyxel to zy 
-- 2. upgrade from SNMP to SNMPv2   
-- 3. clean warning  
-- Revision 1.1  2012/09/10 05:43:18  chchao 
-- Initial revision 
-- Initial revision 

ZYXEL-GREEN-ETHERNET-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelGreenEthernet MODULE-IDENTITY
		LAST-UPDATED	"201207010000Z"    
		ORGANIZATION "Enterprise Solution ZyXEL"     
		CONTACT-INFO
			""	   
		DESCRIPTION
			"The subtree for Green Ethernet"
		::= { esMgmt 93 }

	zyxelGreenEthernetSetup     OBJECT IDENTIFIER ::= { zyxelGreenEthernet 1 }    

--  zyxelGreenEthernetSetup

        zyGreenEthernetEeeState OBJECT-TYPE  
        SYNTAX  EnabledStatus
        MAX-ACCESS  read-write
        STATUS  current
        DESCRIPTION	
        "Enable/Disable EEE"
        ::= { zyxelGreenEthernetSetup 1 }
        
        zyGreenEthernetAutoPowerDownState OBJECT-TYPE
        SYNTAX  EnabledStatus
        MAX-ACCESS  read-write
        STATUS  current
        DESCRIPTION
        "Enable/Disable Auto Power Down"
        ::= { zyxelGreenEthernetSetup 2 }

        zyGreenEthernetShortReachState OBJECT-TYPE
        SYNTAX  EnabledStatus
        MAX-ACCESS  read-write
        STATUS  current
        DESCRIPTION
        "Enable/Disable Short Reach"
        ::= { zyxelGreenEthernetSetup 3 }
                  
        zyxelGreenEthernetPortTable OBJECT-TYPE
        SYNTAX	SEQUENCE OF ZyxelGreenEthernetPortEntry
        MAX-ACCESS  not-accessible
        STATUS  current
        DESCRIPTION
        ""
        ::= { zyxelGreenEthernetSetup 4 }
       
		zyxelGreenEthernetPortEntry OBJECT-TYPE
        SYNTAX	ZyxelGreenEthernetPortEntry
        MAX-ACCESS	not-accessible
        STATUS	current
        DESCRIPTION    	
        "An entry in zyxelGreenEthernetPortTable."
        INDEX          	{ dot1dBasePort }
        ::= { zyxelGreenEthernetPortTable 1 }

        ZyxelGreenEthernetPortEntry ::=
           SEQUENCE {
        	zyGreenEthernetEeePortState				EnabledStatus,
        	zyGreenEthernetAutoPowerDownPortState	EnabledStatus,
        	zyGreenEthernetShortReachPortState		EnabledStatus
           }

        zyGreenEthernetEeePortState OBJECT-TYPE
        SYNTAX  EnabledStatus
        MAX-ACCESS  read-write
        STATUS  current
        DESCRIPTION
        "Enable/Disable EEE by port"
        ::= { zyxelGreenEthernetPortEntry 1 }

		zyGreenEthernetAutoPowerDownPortState OBJECT-TYPE
        SYNTAX  EnabledStatus
        MAX-ACCESS  read-write
        STATUS  current
        DESCRIPTION
        "Enable/Disable Auto Power Down by port"
        ::= { zyxelGreenEthernetPortEntry 2 }          
        
        zyGreenEthernetShortReachPortState OBJECT-TYPE
        SYNTAX  EnabledStatus
        MAX-ACCESS  read-write
        STATUS  current
        DESCRIPTION
        "Enable/Disable Auto Power Down by port"
        ::= { zyxelGreenEthernetPortEntry 3 }

             
END
