-- ZyXEL Communications Corporation
-- Private Enterprise MIB definition 
  
-- This file describes the ZyXEL Communications Corporation Enterprise MIB.
-- It contains ZyXEL products OIDs, and common managed objects.

-- $Log: ZYXEL-CFM-MIB.mib $ 
-- Revision 1.8  2012/12/10 13:40:06  Dana 
-- fix silverCreek can't compile 
-- Revision 1.7  2012/10/26 02:14:43  Dana 
-- rename zyCfmManIpAddressDomain->zyCfmMgmtIpAddressDomain and zyCfmManIpAddress->zyCfmMgmtIpAddress 
-- Revision 1.6  2012/10/23 06:45:48  Dana 
-- fix syntax IpAddress in zyCfmManIpAddress, SNMPc can set it 
-- Revision 1.5  2012/10/04 09:56:33  Dana 
-- change cfm Ccmdb to CcmDb 
-- Revision 1.4  2012/10/03 01:52:22  Dana 
-- add CFM clear cmd into MIB 
-- Revision 1.3  2012/09/19 07:29:51  Kevin 
-- if it's leaf node, revise the vender name from zyxel to zy 
-- Revision 1.2  2012/07/05 06:22:20  Kevin 
-- 1. upgrade from SNMP to SNMPv2  
-- 2. clean warning 
-- Revision 1.1  2012/05/30 07:48:12  Kevin 
-- Initial revision 

ZYXEL-CFM-MIB DEFINITIONS ::= BEGIN

    IMPORTS
	enterprises, Unsigned32		FROM RFC1155-SMI                                
	
	OBJECT-TYPE
		FROM SNMPv2-SMI			-- RFC2578	
	RowStatus, DateAndTime, TruthValue, StorageType, MacAddress ,TDomain, TAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelCfm MODULE-IDENTITY
		LAST-UPDATED	"201207010000Z"    
		ORGANIZATION "Enterprise Solution ZyXEL"     
		CONTACT-INFO
			""	   
		DESCRIPTION
			"The subtree for cfm"
		::= { esMgmt 13 }	
	
	zyxelCfmSetup			OBJECT IDENTIFIER ::= { zyxelCfm 1 }
	zyxelCfmStatus			OBJECT IDENTIFIER ::= { zyxelCfm 2 }	

--  1.zyxelCfmSetup 
	
		  
		    	    
		zyCfmState OBJECT-TYPE
	    SYNTAX      EnabledStatus
	    MAX-ACCESS  	read-write
	    STATUS      current
	    DESCRIPTION
	       "Enabled/disabled CFM on the switch."
	    ::= { zyxelCfmSetup 1 }  

		zyxelCfmMibObjects         OBJECT IDENTIFIER ::= { zyxelCfmSetup 2 }
	
-- ******************************************************************
-- Groups in the CFM MIB Module
-- ******************************************************************
	
-- ******************************************************************
-- The MEP Table
-- ****************************************************************** 
	    zyCfmMgmtIpAddressDomain OBJECT-TYPE
        SYNTAX  TDomain
        MAX-ACCESS  read-write
        STATUS  current
        DESCRIPTION
        "This object indicates the transport type of the address contained in sender ID TLV. 
		 Typical values will be one of (not all inclusive) list:
			transportDomainUdpIpv4  (1.3.6.1.2.1.100.1.1)
			snmpIeee802Domain        (1.3.6.1.6.1.6)"
        ::= { zyxelCfmMibObjects 1 }
 
 	zyCfmMgmtIpAddress OBJECT-TYPE
        SYNTAX  IpAddress
        MAX-ACCESS  read-write
        STATUS  current
        DESCRIPTION
        "The address that can be used to manage the responding MP."
        ::= { zyxelCfmMibObjects 2 }
		
		zyxelCfmMepTable OBJECT-TYPE
	    SYNTAX      SEQUENCE OF ZyxelCfmMepEntry
	    MAX-ACCESS  not-accessible
	    STATUS      current
	    DESCRIPTION
	    "The table contains CFM MEP configuration."
	    ::= { zyxelCfmMibObjects 3 }        
	    
	   	zyxelCfmMepEntry OBJECT-TYPE
	    SYNTAX      ZyxelCfmMepEntry
	    MAX-ACCESS  not-accessible
	    STATUS      current
	    DESCRIPTION
	    "An entry contains CFM MEP configuration. "
	    INDEX { dot1agCfmMdIndex,
	            dot1agCfmMaIndex,
	            dot1agCfmMepIdentifier
	          }
	    ::= { zyxelCfmMepTable 1 }
    
		ZyxelCfmMepEntry ::= SEQUENCE {
	      zyCfmMepTransmitLbmDataTlvSize           Unsigned32	      
	    }
       	    
		zyCfmMepTransmitLbmDataTlvSize OBJECT-TYPE
	    SYNTAX      Unsigned32 (0..1500)
	    MAX-ACCESS  	read-write
	    STATUS      current
	    DESCRIPTION
	    "Size of data to be included in the LBM data TLV."
	    REFERENCE
	       ""
	    ::= { zyxelCfmMepEntry 1 }  

		
--  2.zyxelCfmStatus
		zyCfmLinkTraceClear OBJECT-TYPE
	    SYNTAX      EnabledStatus
	    MAX-ACCESS 	read-write
	    STATUS      current
	    DESCRIPTION
	       "Clears the link trace database."
	    ::= { zyxelCfmStatus 1 }  
		
		zyCfmMepCcmDbClear OBJECT-TYPE
	    SYNTAX      EnabledStatus
	    MAX-ACCESS 	read-write
	    STATUS      current
	    DESCRIPTION
	       "Clears the MEP CCM database."
	    ::= { zyxelCfmStatus 2 }  
		
		zyCfmMepDefectsClear OBJECT-TYPE
	    SYNTAX      EnabledStatus
	    MAX-ACCESS 	read-write
	    STATUS      current
	    DESCRIPTION
	       "Clears the MEP-defects database."
	    ::= { zyxelCfmStatus 3 }  
		
		zyCfmMipCcmDbClear OBJECT-TYPE
	    SYNTAX      EnabledStatus
	    MAX-ACCESS 	read-write
	    STATUS      current
	    DESCRIPTION
	       "Clears the MIP CCM database."
	    ::= { zyxelCfmStatus 4 }  
END
