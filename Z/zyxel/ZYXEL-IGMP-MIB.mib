-- ZyXEL Communications Corporation
-- Private Enterprise MIB definition 
  
-- This file describes the ZyXEL Communications Corporation Enterprise MIB.
-- It contains ZyXEL products OIDs, and common managed objects.

-- $Log: ZYXEL-IGMP-MIB.mib $ 
-- Revision 1.3  2012/09/19 07:36:22  Kevin 
-- if it's leaf node, revise the vender name from zyxel to zy 
-- Revision 1.2  2012/07/05 06:22:52  Kevin 
-- 1. upgrade from SNMP to SNMPv2  
-- 2. clean warning 
-- Revision 1.1  2012/05/30 07:48:42  Kevin 
-- Initial revision 

ZYXEL-IGMP-MIB DEFINITIONS ::= BEGIN

    IMPORTS
	enterprises		FROM RFC1155-SMI                                
	
	OBJECT-TYPE
		FROM SNMPv2-SMI			-- RFC2578	
	RowStatus, DateAndTime, TruthValue, StorageType, MacAddress ,TDomain, TAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
    zyRouteDomainIpAddress, zyRouteDomainIpMaskBits		
		FROM ZYXEL-IP-FORWARD-MIB
	esMgmt			
		FROM ZYXEL-ES-SMI;

	zyxelIgmp MODULE-IDENTITY
		LAST-UPDATED	"201207010000Z"    
		ORGANIZATION "Enterprise Solution ZyXEL"     
		CONTACT-INFO
			""	   
		DESCRIPTION
			"The subtree for Internet Group Management Protocol (IGMP)"
		::= { esMgmt 29 }	

	zyxelIgmpSetup     		OBJECT IDENTIFIER ::= { zyxelIgmp 1 }		

        zyIgmpState OBJECT-TYPE
        SYNTAX  EnabledStatus
        MAX-ACCESS  read-write
        STATUS  current
        DESCRIPTION
        "Enable/Disable IGMP on the switch."
        ::= { zyxelIgmpSetup 1 }

-- 		routerDomainIpTable
        zyxelIgmpRouteDomainTable OBJECT-TYPE
        SYNTAX	SEQUENCE OF ZyxelIgmpRouteDomainEntry
        MAX-ACCESS  not-accessible
        STATUS  current
        DESCRIPTION
        "The table contains IGMP route domain configuration."
        ::= { zyxelIgmpSetup 2 }
        
		zyxelIgmpRouteDomainEntry OBJECT-TYPE
        SYNTAX	ZyxelIgmpRouteDomainEntry
        MAX-ACCESS	not-accessible
        STATUS	current
        DESCRIPTION    	
		"An entry contains IGMP route domain configuration."
        INDEX          	{ zyRouteDomainIpAddress, zyRouteDomainIpMaskBits }
        ::= { zyxelIgmpRouteDomainTable 1 }

        ZyxelIgmpRouteDomainEntry ::=
        SEQUENCE {
        	zyIgmpRouteDomainVersion	INTEGER
            }   
           
        zyIgmpRouteDomainVersion OBJECT-TYPE
        SYNTAX  INTEGER {
        	none(0),
        	igmp-v1(1),
        	igmp-v2(2),
        	igmp-v3(3)
        }
        MAX-ACCESS  read-write
        STATUS  current
        DESCRIPTION
        "IGMP version which controls the format and the multicasting method of the IGMP packets that the switch sends."
        ::= { zyxelIgmpRouteDomainEntry 1 }


END
