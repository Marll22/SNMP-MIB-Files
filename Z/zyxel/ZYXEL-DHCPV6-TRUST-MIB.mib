-- ZyXEL Communications Corporation
-- Private Enterprise MIB definition 
  
-- This file describes the ZyXEL Communications Corporation Enterprise MIB.
-- It contains ZyXEL products OIDs, and common managed objects.

ZYXEL-DHCPV6-TRUST-MIB DEFINITIONS ::= BEGIN

    IMPORTS
	OBJECT-TYPE
		FROM SNMPv2-SMI			-- RFC2578	
		
	MODULE-IDENTITY
		FROM SNMPv2-SMI
	
	EnabledStatus
		FROM  P-BRIDGE-MIB

	dot1dBasePort
       	FROM BRIDGE-MIB

	esMgmt			
		FROM ZYXEL-ES-SMI;

	zyxelDhcpv6Trust MODULE-IDENTITY
		LAST-UPDATED	"201502160000Z"    
		ORGANIZATION "Enterprise Solution ZyXEL"     
		CONTACT-INFO
			""	   
		DESCRIPTION
			"The subtree for DHCPv6 Trust"
		::= { esMgmt 107 }	

	zyxelDhcpv6TrustSetup   	OBJECT IDENTIFIER ::= { zyxelDhcpv6Trust 1 }
		
 -- ******************************************************************
-- *
-- 107. zyxelDhcpv6TrustSetup
-- *
-- ****************************************************************** 
                               
        zyDhcpv6TrustState OBJECT-TYPE
        SYNTAX  EnabledStatus
        MAX-ACCESS  read-write
        STATUS  current
        DESCRIPTION
        "Enable/Disable DHCPv6 Trust on the switch."
        ::= { zyxelDhcpv6TrustSetup 1 }

                                               
-- 		zyxelDhcpv6TrustPortTable

		zyxelDhcpv6TrustPortTable OBJECT-TYPE
		SYNTAX	SEQUENCE OF ZyxelDhcpv6TrustPortEntry
        MAX-ACCESS  not-accessible
        STATUS  current
        DESCRIPTION
        "The table contains DHCPv6 Trust port configuration."
        ::= { zyxelDhcpv6TrustSetup 2 }
        
		zyxelDhcpv6TrustPortEntry OBJECT-TYPE
        SYNTAX	ZyxelDhcpv6TrustPortEntry
        MAX-ACCESS	not-accessible
        STATUS	current
        DESCRIPTION    	
		"An entry contains DHCPv6 Trust port configuration."
        INDEX          	{ dot1dBasePort }
        ::= { zyxelDhcpv6TrustPortTable 1 }
     
		ZyxelDhcpv6TrustPortEntry ::=
		SEQUENCE {
			zyDhcpv6TrustPortState	 INTEGER
		}

        zyDhcpv6TrustPortState OBJECT-TYPE
        SYNTAX  EnabledStatus
        MAX-ACCESS  read-write
        STATUS  current
        DESCRIPTION
        "Enable/Disable this port to be a trusted port (enable) or an un-trusted port(disable)."
        ::= { zyxelDhcpv6TrustPortEntry 1 }

END
