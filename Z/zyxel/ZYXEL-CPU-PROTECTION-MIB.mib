-- ZyXEL Communications Corporation
-- Private Enterprise MIB definition 
  
-- This file describes the ZyXEL Communications Corporation Enterprise MIB.
-- It contains ZyXEL products OIDs, and common managed objects.

-- $Log: ZYXEL-CPU-PROTECTION-MIB.mib $ 
-- Revision 1.3  2012/09/19 07:30:23  Kevin 
-- if it's leaf node, revise the vender name from zyxel to zy 
-- Revision 1.2  2012/07/05 06:22:25  Kevin 
-- 1. upgrade from SNMP to SNMPv2  
-- 2. clean warning 
-- Revision 1.1  2012/05/30 07:48:07  Kevin 
-- Initial revision 

ZYXEL-CPU-PROTECTION-MIB DEFINITIONS ::= BEGIN

    IMPORTS
	enterprises		FROM RFC1155-SMI                                
	
	OBJECT-TYPE
		FROM SNMPv2-SMI			-- RFC2578	
	RowStatus, DateAndTime, TruthValue, StorageType, MacAddress ,TDomain, TAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelCpuProtection MODULE-IDENTITY
		LAST-UPDATED	"201207010000Z"    
		ORGANIZATION "Enterprise Solution ZyXEL"     
		CONTACT-INFO
			""	   
		DESCRIPTION
			"The subtree for cpu protection"
		::= { esMgmt 16 }	

	zyxelCpuProtectionSetup 		OBJECT IDENTIFIER ::= { zyxelCpuProtection 1 }		

-- ******************************************************************
-- *
-- 16. zyxelCpuProtection
-- *
-- ****************************************************************** 

     	zyxelCpuProtectionTable	OBJECT-TYPE
        SYNTAX	SEQUENCE OF ZyxelCpuProtectionEntry
        MAX-ACCESS  not-accessible
        STATUS  current
        DESCRIPTION
        "The table contains CPU protection configuration."
        ::= { zyxelCpuProtectionSetup 1 }   
        
		zyxelCpuProtectionEntry OBJECT-TYPE
        SYNTAX	ZyxelCpuProtectionEntry
        MAX-ACCESS	not-accessible
        STATUS	current
        DESCRIPTION    	
		"An entry contains CPU protection configuration."
        INDEX          	{ zyCpuProtectionPort, zyCpuProtectionReasonType}
        ::= { zyxelCpuProtectionTable 1 }

        ZyxelCpuProtectionEntry ::=
		SEQUENCE {
        	zyCpuProtectionPort       	INTEGER,
        	zyCpuProtectionReasonType	INTEGER,
        	zyCpuProtectionRateLimit 	INTEGER
          }
                
        zyCpuProtectionPort OBJECT-TYPE
        SYNTAX  INTEGER           
        MAX-ACCESS  not-accessible
        STATUS  current
        DESCRIPTION
        "This field displays the port number."
        ::= { zyxelCpuProtectionEntry 1 }      
        
        
        zyCpuProtectionReasonType OBJECT-TYPE
        SYNTAX  INTEGER{
	        arp(1),
	        bpdu(2),
		    igmp(3)
        }
        MAX-ACCESS  not-accessible
        STATUS  current
        DESCRIPTION
        "This field displays which type of control packets on the specified port."
        ::= { zyxelCpuProtectionEntry 2}    
        

        zyCpuProtectionRateLimit OBJECT-TYPE
        SYNTAX  INTEGER(0..256)
        MAX-ACCESS  read-write
        STATUS  current
        DESCRIPTION
        "Enter a number from 0 to 256 to specified how many control packets this port can receive or transmit per second. 
		 0 means no rate limit."
        ::= { zyxelCpuProtectionEntry 3}    
        
                          
END
