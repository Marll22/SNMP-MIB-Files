-- ZyXEL Communications Corporation
-- Private Enterprise MIB definition 
  
-- This file describes the ZyXEL Communications Corporation Enterprise MIB.
-- It contains ZyXEL products OIDs, and common managed objects.

-- $Log: ZYXEL-IPV6-PATH-MTU-MIB.mib $ 
-- Revision 1.3  2012/09/19 07:38:31  Kevin 
-- if it's leaf node, revise the vender name from zyxel to zy 
-- Revision 1.2  2012/07/05 06:23:10  Kevin 
-- 1. upgrade from SNMP to SNMPv2  
-- 2. clean warning 
-- Revision 1.1  2012/05/30 07:49:40  Kevin 
-- Initial revision 

ZYXEL-IPV6-PATH-MTU-MIB DEFINITIONS ::= BEGIN

    IMPORTS
	enterprises		FROM RFC1155-SMI                                
	
	OBJECT-TYPE, Gauge32
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelIpv6PathMtu MODULE-IDENTITY
		LAST-UPDATED	"201207010000Z"    
		ORGANIZATION "Enterprise Solution ZyXEL"     
		CONTACT-INFO
			""	   
		DESCRIPTION
			"The subtree for IPv6 Path MTU"
		::= { esMgmt 36 }
	
	zyxelPathMtuDiscoveryStatus	OBJECT IDENTIFIER ::= { zyxelIpv6PathMtu 1 }
	
---------------------------------------------------
--
--  36.Ipv6PathMtu 
--
---------------------------------------------------	                   
        
--	zyxelPathMtuTable
		zyxelPathMtuDiscoveryTable	OBJECT-TYPE
        SYNTAX	SEQUENCE OF ZyxelPathMtuDiscoveryEntry
        MAX-ACCESS  not-accessible
        STATUS  current
        DESCRIPTION	
		"The table contains path MTU discovery information."
        ::= { zyxelPathMtuDiscoveryStatus 1 }    

		zyxelPathMtuDiscoveryEntry OBJECT-TYPE
        SYNTAX	ZyxelPathMtuDiscoveryEntry
        MAX-ACCESS	not-accessible
        STATUS	current
        DESCRIPTION    	
        "An entry contains path MTU discovery information."
        INDEX          	
        { 
        	zyPathMtuDiscoveryDestinationIpAddressType,
        	zyPathMtuDiscoveryDestinationIpAddress 
        }
        ::= { zyxelPathMtuDiscoveryTable 1 }

        ZyxelPathMtuDiscoveryEntry ::=
		SEQUENCE 
		{
        	zyPathMtuDiscoveryDestinationIpAddressType	InetAddressType,
        	zyPathMtuDiscoveryDestinationIpAddress		InetAddress,
        	zyPathMtuDiscoveryMtu						INTEGER,
        	zyPathMtuDiscoveryExpiredTime				Gauge32 
        }

        zyPathMtuDiscoveryDestinationIpAddressType OBJECT-TYPE
        SYNTAX  InetAddressType
        MAX-ACCESS  not-accessible
        STATUS  current
        DESCRIPTION	
        "The destination address type in the message body of ICMPv6 packet too big error message."
        ::= { zyxelPathMtuDiscoveryEntry 1 }     
 
        zyPathMtuDiscoveryDestinationIpAddress OBJECT-TYPE
        SYNTAX  InetAddress
        MAX-ACCESS  not-accessible
        STATUS  current
        DESCRIPTION	
        "The destination address in the message body of ICMPv6 packet too big error message."
        ::= { zyxelPathMtuDiscoveryEntry 2 }  

        zyPathMtuDiscoveryMtu OBJECT-TYPE
        SYNTAX  INTEGER
        MAX-ACCESS  read-only
        STATUS  current
        DESCRIPTION	
        "The MTU in the ICMPv6 packet too big error message."
        ::= { zyxelPathMtuDiscoveryEntry 3 }         

        zyPathMtuDiscoveryExpiredTime OBJECT-TYPE
        SYNTAX  Gauge32
        MAX-ACCESS  read-only
        STATUS  current
        DESCRIPTION	
        "The aging time of each entry in the path MTU discovery table."
        ::= { zyxelPathMtuDiscoveryEntry 4 }  

END
