-- Copyright 2021 Grandstream Networks, Inc. All Rights Reserved.

GRANDSTREAM-GWN-ROOT-MIB DEFINITIONS ::= BEGIN

IMPORTS
    enterprises,
    MODULE-IDENTITY
        FROM SNMPv2-SMI;

grandstreamRootMIB MODULE-IDENTITY
    LAST-UPDATED "202110280001Z"
    ORGANIZATION "Grandstream Networks, Inc."
    CONTACT-INFO
        "Grandstream Networks, Inc.

        Web: www.grandstream.com"
    DESCRIPTION
        "Grandstream top level mib."
    ::= { enterprises 42397 }

-- Groups
--

-- 1.3.6.1.4.1.42397.1
gwnProducts OBJECT IDENTIFIER ::= { grandstreamRootMIB 1 }



END
